-- ============================================================================
-- Copyright (C) 2017 by HUAWEI TECHNOLOGIES. All rights reserved.
-- Description:	The MIB module defines MIB objects which provide device
--              management NMS interfaces.
-- Reference:   
-- Version:     V4.72
-- ============================================================================
	HUAWEI-DEVICE-MIB DEFINITIONS ::= BEGIN 
	
	IMPORTS      
        MODULE-COMPLIANCE, NOTIFICATION-GROUP, OBJECT-GROUP
                FROM SNMPv2-CONF
		TimeTicks, IpAddress, Integer32, Unsigned32, OBJECT-TYPE, MODULE-IDENTITY,
		NOTIFICATION-TYPE
			FROM SNMPv2-SMI
		DisplayString, DateAndTime, TruthValue, RowStatus
			FROM SNMPv2-TC
		HWFrameType, HWPCBType, HWSubPCBType, HWPortType
			FROM HUAWEI-TC-MIB
		ifIndex
                        FROM IF-MIB
		 CounterBasedGauge64 
                        FROM HCNUM-TC   
		huaweiUtility
                    FROM HUAWEI-MIB
		InetAddressType, InetAddress
                    FROM INET-ADDRESS-MIB;

    hwDev MODULE-IDENTITY
        LAST-UPDATED "201708170000Z"
            ORGANIZATION
                  "Huawei Technologies Co.,Ltd."
            CONTACT-INFO
                  "Huawei Industrial Base
                    Bantian, Longgang
                     Shenzhen 518129
                     People's Republic of China
                     Website: http://www.huawei.com
                     Email: support@huawei.com
                   "
        DESCRIPTION 
                   "
                    The MIB module defines MIB objects which provide device
                    management NMS interfaces.
                    "
--  Revision history
                REVISION "201708170000Z"
                DESCRIPTION "V4.72, Changed node's DESCRIPTION: 
                             hwCpuDevIndex
                             hwCpuDevDuty 
                             hwAvgDuty1min
                             hwAvgDuty5min
                            "
                REVISION "201707170000Z"
                DESCRIPTION "V4.71, Added the following node: 
                             hwDevSubBoardTemperatureTooHighTrap
                             hwDevSubBoardTemperatureTooHighRecoverTrap 
                             hwDevSubBoardFaultTrap
                             hwDevSubBoardFaultRecoverTrap
                             "
                REVISION "201706290000Z"
                DESCRIPTION "V4.70, 
                            Added hwDevSnmpProbeMonitorActiveThreshold.
                            "
                            
                REVISION "201706140000Z"
                DESCRIPTION "V4.69, 
                            Modify the string length of hwPortDesc from 64 to 80.
                            "

                REVISION "201706080000Z"
                DESCRIPTION "V4.68, 
                            1.Added hwOntRemoteHttpChnlCfgTable.
                            2.Added hwOntRemoteHttpChnlCfgEntry.
                            3.Added the following nodes:
                            hwOntRemoteHttpChnlVlan
                            hwOntRemoteHttpChnlIpAddress
                            hwOntRemoteHttpChnlHttpPort
                            hwOntRemoteHttpChnlProtocol
                            hwOntRemoteHttpChnlUserName
                            hwOntRemoteHttpChnlPassword 
                            hwOntRemoteHttpChnlDuration
                            hwOntRemoteHttpProxyPort
                            hwOntRemoteHttpProxyStatus
                            hwOntRemoteHttpChnlRowStatus.
                            "

                REVISION "201705030000Z"
                DESCRIPTION "V4.67, Add hwSysMarketScene to hwSystemPara for indicating the device market scene."

                REVISION "201704120000Z"
                DESCRIPTION "V4.66, 
                            1.Added hwDevSnmpProbeMonitor.
                            2.Added the following nodes:
                            hwDevSnmpHostIpAddress
                            hwDevSnmpLastReceivedTime
                            hwDevSnmpAverageInterval
                            hwDevSnmpMinimumInterval
                            hwDevSnmpMaxmumInterval
                            hwDevSnmpReceivedCount 
                            hwDevSnmpProbeRecordTrap.
                            "

                REVISION "201703030000Z"
                DESCRIPTION "V4.65, Added the following node: 
                             hwSysFtpMode
                             "
                REVISION "201702090000Z"  
                DESCRIPTION "V4.64, 
                             1. Modify the following nodes:
                             hwbandwidthmode
                            "

                REVISION "201701200000Z"
                DESCRIPTION "V4.63, Added the following node: 
                             hwDeviceCurrentTemp
                             hwDevTempMinorAlmThreshold 
                             hwDevTempMajorAlmThreshold
                             hwDevTempCriticalAlmThreshold
                             hwDeviceHighTemperatureMinorFaultTrap
                             hwDeviceHighTemperatureMinorRestoreTrap
                             hwDeviceHighTemperatureMajorFaultTrap
                             hwDeviceHighTemperatureMajorRestoreTrap
                             hwDeviceHighTemperatureCriticalFaultTrap
                             hwDeviceHighTemperatureCriticalRestoreTrap.
                             "

                REVISION "201701100000Z"
                DESCRIPTION "V4.62, Added the following node: 
                             hwSysSsdSwitch.
                             "
                                                          
                REVISION "201610260000Z"
                DESCRIPTION "V4.61, Added the following nodes: 
                             hwDevLongitude
                             hwDevLatitude
                             hwDevElevation
                             hwDevHorizontalErr
                             hwDevAltitudeErr
                             hwDevAreaCode
                             hwDevGisTimeStamp
                             hwDevGisDigest
                             hwDevGisCheckCode.
                             "
                REVISION "201607260000Z"
                DESCRIPTION "V4.60, Added hwVsPortTable."

                REVISION "201607070000Z"
                DESCRIPTION "V4.59, Modify the SYNTAX of the node hwTrapPowerPortIndex" 
			     
		REVISION "201606230000Z"
                DESCRIPTION "V4.58, Add one node hwPortVsIDMask on hwPortEntry."

                REVISION "201606030000Z"
                DESCRIPTION "V4.57, Added the following nodes: 
                             hwTrapPowerPortIndex
                             hwDevPowerPortInputFaultTrap
                             hwDevPowerPortInputRecoverTrap.
                             " 

                REVISION "201506040000Z"
                DESCRIPTION "V4.56, Added the following nodes: 
                             hwMemOccupancy
                             hwCpuOccupancy
                             " 
			     			 
                REVISION "201501120000Z"
                DESCRIPTION "V4.55, 
                             1. Modify the string length of hwFrameHardwareDesc from 128 to 510.
                             2. Modify the description of the node hwSlotOperStatus.
                             3. Modify the description of the node hwDevBoardReplaceFailTrap.
                             "   
				
                REVISION "201501040000Z"
                DESCRIPTION "V4.54
                             Add enum number nativetdm(11) for hwSlotWorkMode.
			     "
                REVISION "201412050000Z"  
                DESCRIPTION "
                            1. V4.53, Add one node hwDevBoardReplaceFailTrap on hwDevBoardTrapsPrefix.
                            2. using daughter board to replace subboard 
                            "                
                REVISION "201412040000Z"  
                DESCRIPTION "V4.52, Modify the description of the node hwConfigLockUserIPAddr
                             "  

                REVISION "201412010000Z"  
                DESCRIPTION "V4.51, Added the following nodes:
                             hwBandwidth
                             hwBandwidthMode
                            "                

                REVISION "201410230000Z"  
                DESCRIPTION "V4.50, Add one node hwFramePhySerialNum on HwFrameEntry
                            "   
                REVISION "201410150000Z"  
                DESCRIPTION "V4.49, Add one enum number for hwConfigLockUserType:
                             ssh(6)   
                            "     
                            
                REVISION "201410120000Z"  
                DESCRIPTION "V4.48, 
                             1. Modified the MAX-ACCESS of hwNmsStatus frome read-write to read-create.
                             2. Modified the MAX-ACCESS of hwFrameLinkRowStatus frome read-write to read-create.
                             3. Changed the name of hwAlarmType to hwObsoleteAlarmType.
                             4. Modified the INDEX of hwPingAutoResetEntry,delete 'IMPLIED'.   
                            "       
                            
                REVISION "201409170000Z"  
                DESCRIPTION "V4.47, 
                             1. Modify the following nodes:
                             hwSlotPrimaryStatus
                            " 
                
                REVISION "201408060000Z"  
                DESCRIPTION "V4.46, 
                             1. Added the following nodes:
                             hwDevLedLight
                             hwDevLedLightByNms
                            " 

                REVISION "201407300000Z"  
                DESCRIPTION "V4.45, 
                             Added the following nodes:
                             hwVccLocalChassisId
                             hwVccNeighbourChassisId
                             hwVccGroupId
                             hwVccLinkIfPhysicIndex
                             hwVccLinkIfPhysicName
                             hwVccDataLinkFault
                             hwVccDataLinkFaultResume
                             hwVccDataChannelFault
                             hwVccDataChannelFaultResume
                            " 

                REVISION "201407150000Z"  
                DESCRIPTION "V4.44, 
                             1. Modified the sequence of hwFrameTypeName and hwFrameOperStatus in hwDevFrameDetectTrap.
                            " 

                REVISION "201407010000Z"  
                DESCRIPTION "V4.43, 
                             Merage VRP and IAS'S mib together.
                            " 
			    
                REVISION "201406300000Z"  
                DESCRIPTION "V4.42, 
                             1. Added the following nodes:
                             hwDevAutoDeployPhase
                             hwDevSystemAutoDeployFailTrap
                            " 

                
                REVISION "201406060000Z"  
                DESCRIPTION "V4.41, 
                             1. Modify the value range of the node hwSystemEnergySavingSwitch." 
                             
                REVISION "201405090000Z"  
                DESCRIPTION "V4.40, 
                             1. Add enumerated value hotreset(16) in hwSlotAdminStatus.
                             2. Modify the value range of the node hwSubslotCpuRate and hwSubslotRamUseRate." 

                REVISION "201404250000Z"
                DESCRIPTION "V4.39, 
                             1. Added the following nodes:
                             hwDevSystemPoweroffTrap 
                             hwDevBoardInputFaultTrap  
                             hwDevBoardInputRecoverTrap                             
                             hwDevPowerLackVoltageFaultTrap
                             hwDevPowerLackVolitageRecoverTrap 
                             hwSlotInputIdIndex
                             hwSlotInputType.   
                            " 
                            
                REVISION "201404170000Z"  
                DESCRIPTION "V4.38, Modify the value range of the node hwDevAuxiliaryHardwareFaultTrap." 

                REVISION "201404170000Z"  
                DESCRIPTION "V4.37, 
                             1. Add the node hwTrapHardFaultName for the trap hwDevBoardHardFaultTrap and hwDevBoardHardRestoreTrap.
                             2. Add the node hwTrapHardFaultEffect for the trap hwDevBoardHardFaultTrap and hwDevBoardHardRestoreTrap." 

                REVISION "201404100000Z"  
                DESCRIPTION "V4.36, Add hwDevActiveStandbyDataSynCancelTrap and hwDevActiveStandbyDataSynCancelRecoverTrap." 
                REVISION "201403100000Z"  
                DESCRIPTION "V4.35, Modify the description of the node hwFrameExtendPort." 
               
                REVISION "201403070000Z"  
                DESCRIPTION "V4.34, Modify the description of the node hwPortOperStatus."

                REVISION "201402140000Z"  
                DESCRIPTION "V4.33, Modify the description and the value range of the node hwDevFrameCmtsAntitheftAuthFailTrap and hwDevFrameCmtsAntitheftAuthRestoreTrap."

                REVISION "201402120000Z" 
                DESCRIPTION "V4.32, 
                             1. Add the node hwExtendBoardSlotIndex for geting the slot index of board connected to extended frame.
                             2. Add the node hwExtendBoardPortIndex for geting the port index of board connected to extended frame." 

                REVISION "201401210000Z" 
                DESCRIPTION "V4.31, 
                             1. Add hwDevFrameCmtsAntitheftAuthFailTrap and hwDevFrameCmtsAntitheftAuthRestoreTrap for D-CMTS anti-theft." 

                REVISION "201401140000Z" 
                DESCRIPTION "V4.30, Modify the appended node order for trap node hwDevSubBoardReplacedTrap." 

        REVISION "201311180000Z" 
                DESCRIPTION "V4.29, Add the node hwUpgradeVerifyVersion for getting the version of system." 

                REVISION "201308170000Z" 
                DESCRIPTION "V4.28, add the Node hwSlotCreateTime for getting the time of adding or creating a board in the hwSlotTable."
                
                REVISION "201307220000Z" 
                DESCRIPTION "V4.27, Modify the hwNatOnuMgmtSwitch type, from Integer32 to INTEGER." 

        REVISION "201306250000Z"
                DESCRIPTION "V4.26, Add the appended node hwDevAuxiliaryHardwareFaultTrap for trap node hwDevBoardTraps."

                REVISION "201306200000Z"
                DESCRIPTION "V4.25, 
                             1. Modify the hwServiceMigrationOntId and hwServiceCfgOntId node description."
                             
                REVISION "201306080000Z"
                DESCRIPTION "V4.24, 
                             1. Modify the value range of the node hwOntIndex.
                             2. Add the appended node hwSysVersion for trap node hwFtpConfigureTrap."

                REVISION "201306030000Z"
                DESCRIPTION "V4.23, 
                             1. Modify the value range of the node hwFrameGponDeviceSn and the description.
                             2. Modify the value range of the node hwPortDesc."

                REVISION "201305221200Z"
                DESCRIPTION "V4.22, Modify the hwServiceCfgOperStatus values and description."
                
                REVISION "201304281200Z"
                DESCRIPTION "V4.21, Add hwSysCentralizedMgmtPrimary in hwSystemPara table."
 
                REVISION "201304020000Z"
                DESCRIPTION "V4.20,
                             1. Add hwFrameGponDeviceSn in hwFrameTable.
                             2. Modify hwFrameExtendingSubId and hwFrameAdminStatus for remote frame.
                             3. Add hwDevFrameIdOverLoadTrap in hwDevFrameTraps."                

                REVISION "201303280000Z"
                DESCRIPTION "V4.19, Modify the value range of the node hwSubslotAdminStatus."

                REVISION "201301160000Z"
                DESCRIPTION "V4.18, Add hwFrameExtendType, hwFrameExtendingSubId, hwFrameHardwareDesc for remote frame"
                         
                REVISION "201301110000Z"
                DESCRIPTION "V4.17, Add hwFtpConfigureTrap, hwDevBoardAutomaticExpandFailTrap, hwDevBoardAutomaticExpandRestoreTrap 
                         for board expand trap"

                REVISION "201212180000Z"
                DESCRIPTION "V4.16, Modify hwSysSceneMode for deleting the item dslam and all. And added hwDevStorageFaultRestoreTrap for certain storage fault"

                REVISION "201212110000Z"
                DESCRIPTION "V4.15, Modify the value range of the node hwFrameOperStatus."                      
                        
                REVISION "201210260000Z"
                DESCRIPTION "V4.14, Add hwSysCapabilityTable."

                REVISION "201210260000Z"
                DESCRIPTION "V4.12, Add hwSysFtpXmlConfigure in hwSystemPara for deciding the XML file can be deleted."  

                REVISION "201210230000Z"
                DESCRIPTION "V4.11, 
                        1. Modify the value range of the node hwSubslotOperStatus.
                        2. Add hwSubslotCpuRate and hwSubslotRamUseRate in hwSubslotTable."  

                REVISION "201210200000Z" 
                DESCRIPTION "V4.10, Add enumerated value extend(4) in hwPortNetworkRole."
                
                REVISION "201209040000Z"
                DESCRIPTION "V4.09, Add hwDevExtendedFrameDyingGaspAlarmTrap, hwDevExtendedFrameDyingGaspRestoreTrap for remote frame dying gasp alarm."  
                
                REVISION "201208230000Z"
                DESCRIPTION "V4.08, Modify the string length of hwSlotDesc from 64 to 32." 

                REVISION "201208160000Z"
                DESCRIPTION "V4.07, 1. Modify the string length of hwFrameDesc from 64 to 128.
                             2. Add hwFrameRackID in hwFrameEntry for indicating the rack ID of the frame.
                             3. Modify the description of the node hwFrameTypeConfigured and hwDevExtendedFrameTypeInconsistentTrap." 

                REVISION "201208020000Z"
                DESCRIPTION "V4.06, 1.Modify description of autoshutdown of hwSlotOperStatus node.
                             2. Add AC Power shutdown value for hwSlotOperStatus node." 

                  REVISION "201207260000Z"
                DESCRIPTION "V4.05, Added hwSubslotTemperature in hwSubslotEntry." 

                REVISION "201207090000Z"
                DESCRIPTION "V4.04, 
                             1. Added the following nodes: 
                             hwFrameExtendPort  
                             hwFrameUplinkPort                             
                             hwDevFrameDetectTrap
                             hwDevFrameDisappearedTrap
                             hwDevFrameStateChangeTrap 
                             hwDevExtendedFramePortChangeTrap
                             hwDevFrameRestoreTrap
                             hwDevFrameFaultTrap
                             hwExtendBoardFrameIndex 
                             hwExtendedFrameUplinkPort
                             hwDevExtendedFrameTypeInconsistentTrap.   
                             2. Added mismatch(5) in hwFrameOperStatus. 
                             3. Added extend(4) in hwSlotNetworkRole.
                             4. Added hwServiceMigrationTable and hwServiceCfgMngtTable.
                            "  
                        
                REVISION "201206290000Z"
                DESCRIPTION "V4.03, Add hwSysSceneMode to hwSystemPara for indicating the work scene of device."  

                REVISION "201206120000Z"
                DESCRIPTION "V4.02, 1. Modify the description of hwConfigChangeIP.
                             2. Modify the enum description of hwSlotOperStatus from discovery(5) to autofind(5)." 

                REVISION "201205230000Z"
                DESCRIPTION "V4.01, 1. Add hwSysEnergySaving in hwSystemPara."            

                REVISION "201205140000Z"
                DESCRIPTION "V4.01, Added the following node for hwDevBoardFpgaFailTrap and hwDevBoardFpgaRestoreTrap:
                             hwTrapHardFaultPara2."    
                                
                REVISION "201203220000Z"
                DESCRIPTION "V4.00, 1. Renamed the hwDevSystemManualResetTrap to hwDevSystemResetTrap.             
                             2.  Modified the description of hwUpgradeReserveDateTime, hwDevSystemResetTrap."    
                             
                REVISION "201203160000Z"
                DESCRIPTION "V3.99, 1. Added frequency20HZ(4) in hwRingFrequency.             
                             2. Added acamplitude70Vrms(5) in hwRingacamplitude."    
                                    
                REVISION "201202210000Z"
                DESCRIPTION "V3.98, Modify the description of hwSlotTemprature.
                             Modify hwUpgradeCapability description to From left to right.                  
                             Add two enum number for hwSlotWorkMode:9.(bonding) and 10.(retransmission)."                
        
                REVISION "201202100000Z"
                DESCRIPTION "V3.97, 1. Modified the description of hwUpgradeRequestID, hwUpgradeReserveTimeout."

                REVISION "201202080000Z"
                DESCRIPTION "V3.96, Modify hwSysTemperatureHighThreshold range from
                             40~110 to 40~105"
                
                REVISION "201201040000Z"
                DESCRIPTION "V3.95, Add three enum number for hwSlotWorkMode:
                             eocLoopbackNoTest(57),
                             eocLoopbackTest(58),
                             prohibited(59)"
                             
                REVISION "201112220000Z"
                DESCRIPTION "V3.94, Modified the SYNTAX of hwAppBoardMngtIp of hwAppBoardMngtEntry from  IpAddress to InetAddress.
                             Modified the SYNTAX of hwAppBoardMngtGateway of hwAppBoardMngtEntry from IpAddress to InetAddress."

                REVISION "201112090000Z"
                DESCRIPTION "V3.93, Added hwDevBoardFpgaFailTrap for software fault occurs in board FPGA.
                             Added the following nodes:
                             hwSlotTypeName.
                             Added hwDevBoardFpgaRestoreTrap for software fault in board FPGA recovers.
                             Added the following nodes:
                             hwSlotTypeName." 
        
                REVISION "201111150000Z"
                DESCRIPTION "V3.92, Added interruptedAutoUpgrade(4) in hwSoftwareActiveAdmin.
                             Added hwUpgradeCapability in hwSoftwareActive.
                             Added hwEmergencyCallProtect in hwSoftwareActive.
                             Modified all nodes's name of hwSoftwareActive from SoftwareActive to Upgrade for upgrade.
                             Modified the following nodes of the table: 
                             hwSoftwareActiveRequestID        -->  hwUpgradeRequestID
                             hwSoftwareActiveAdmin            -->  hwUpgradeAdmin 
                             hwSoftwareActiveResetInterval    -->  hwUpgradeResetInterval
                             hwSoftwareActiveTargetVersion    -->  hwUpgradeTargetVersion
                             hwSoftwareActiveReserveTimeout   -->  hwUpgradeReserveTimeout 
                             hwSoftwareActiveReserveDateTime  -->  hwUpgradeReserveDateTime" 
                
                REVISION "201111090000Z"
                DESCRIPTION "V3.91, Modified the description of hwSubslotIndex,hwSysTemperatureHighThreshold,hwSysTemperatureLowThreshold."
                
                REVISION "201111040000Z"
                DESCRIPTION "V3.90, Modified the description of hwSysTemperatureHighThreshold." 

                REVISION "201110240000Z"
                DESCRIPTION "V3.89, Added hwDevStorageFaultTrap for certain storage fault.
                             Added the following nodes:
                             hwTrapStorageName" 

                REVISION "201109150000Z"
                DESCRIPTION "V3.88, Add hwSysMainBoardTypeDesc in hwSystemPara."

                REVISION "201108270000Z"
                DESCRIPTION "V3.87, Added initial value(-1) in hwSoftwareActiveAdmin and hwSoftwareActiveResetInterval."
                
                REVISION "201108180000Z"
                DESCRIPTION "V3.86, Modified all nodes's name of hwAcBoardPara from Ac to App for managing general application board.
                             Modified the following nodes of the table:  
                             hwAcBoardMngtVlan        -->  hwAppBoardMngtVlan
                             hwAcBoardMngtIpType      -->  hwAppBoardMngtIpType
                             hwAcBoardMngtIp          -->  hwAppBoardMngtIp
                             hwAcBoardMngtMaskLength  -->  hwAppBoardMngtMaskLength
                             hwAcBoardMngtGateway     -->  hwAppBoardMngtGateway
                             hwAcBoardMngtRowStatus   -->  hwAppBoardMngtRowStatus.
                             Modified the SYNTAX of hwAppBoardMngtIp from InetAddress to IpAddress.
                             Modified the SYNTAX of hwAppBoardMngtGateway from InetAddress to IpAddress."
                             
                REVISION "201108080000Z"
                DESCRIPTION "V3.85, Add hwUplinkSysIPAddr in hwSystemPara."
                             
                REVISION "201107180000Z"
                DESCRIPTION "V3.84, Renamed the hwAutoUpgrade to hwSoftwareActive.
                             Added hwSoftwareActiveReserveTimeout and hwSoftwareActiveReserveDateTime in hwSoftwareActive." 
            
                REVISION "201107090000Z"
                DESCRIPTION "V3.83, Rename the enum of hwSystemAdminStateMode frome north-america to grStandard." 

                REVISION "201106150000Z"
                DESCRIPTION "V3.82, Modified the MAX-ACCESS of hwSlotShutdownState frome read-create to read-only.
                             Added the UNITS of hwSlotTemprature." 

                REVISION "201103010000Z"
                DESCRIPTION "V3.81, Modified the SYNTAX of hwOldSubslotType0, hwOldSubslotType1,hwOldSubslotType2 and hwOldSubslotType3,
                             the SYNTAX value from Integer32 changed to HWSubPCBType." 

                REVISION "201101190000Z"
                DESCRIPTION "V3.80, Add two enum number for hwSlotWorkMode:7.(pots) and 8.(isdn)" 
                
                REVISION "201011060000Z"
                DESCRIPTION "V3.79, Added hwDevBoardPower5VFaultTrap and hwDevBoardPower5VResumeTrap. Modified the description of hwDevBoardOnlineStateTrap. 
                             Modified the description of hwNmsParaEntry, hwFrameEntry, hwSlotEntry, hwSubslotEntry,hwPortEntry,hwPortOperStatus,
                             hwFrameLinkEntry,hwMemoryDevEntry,hwBufferEntry,hwFlashDevEntry,hwAlarmEntry,hwDevConfPreviousTable,hwDevConfPreviousEntry, 
                             hwCustomizedParameterEntry,hwPingAutoResetEntry,hwSystemResEntry,hwAgentOntInfoEntry,hwPstnBoardCfgEntry,hwPowerMode." 
                             
                REVISION "201011010000Z"
                DESCRIPTION "V3.78, Added hwDevBoardHardRestoreTrap for standard trap." 
                
                REVISION "201010080000Z"
                DESCRIPTION "V3.77, Modified the description of hwSlotTemprature, hwSysTemperatureLowThreshold and hwSysTemperatureHighThreshold." 
    
                REVISION "201009200000Z"
                DESCRIPTION "V3.76, Added initial value(-1) in hwFrameResetTimeout." 

                REVISION "201009020000Z"
                DESCRIPTION  "V3.75, Add hwSubslotCLEICode of elabel CLEI in hwSubslotTable."
                        
                REVISION "201008020000Z"
                DESCRIPTION "V3.74, modified and supplemented the descriptions of objects in hwPortTable, hwFrameTable, hwSlotTable, hwSubslotTable 
                             and hwDevTraps.
                             Changed the name of hwAlarmType to hwObsoleteAlarmType.
                             Added enumerated value deactivepacketfile(0) in hwIopacketfileAdminStatus.
                             Added enumerated value user(3) in hwSlotNetworkRole.                             
                             Added hwSystemResParaTable for standard trap" 
                
                REVISION "201007280000Z"
                DESCRIPTION "V3.73, Add hwAcBoardGlobalPara, for managing the AC board. 
                             The following leaf nodes are added to the table:  
                             hwAcBoardPhySlot." 
                
                REVISION "201007150000Z"
                DESCRIPTION "V3.72, added hwDevStandbyMainSlotTypeName and hwDevConfPreviousTable for standard trap.
                             Modified the objects of hwDevActiveStandbyContolBoardInconsistentTrap and hwDevBoardReplacedTrap."                                                           
                
                REVISION "201007120000Z"
                DESCRIPTION "V3.71, added hwAcBoardMngtTable for managing the AC board. 
                             Added the following nodes to the table:  
                             hwAcBoardMngtVlan
                             hwAcBoardMngtIpType 
                             hwAcBoardMngtIp 
                             hwAcBoardMngtMaskLength
                             hwAcBoardMngtGateway
                             hwAcBoardMngtRowStatus"  
                        
                REVISION "201006240000Z"
                DESCRIPTION "V3.70, added hwDeviceArchType in hwSystemPara.
                             Added hwDevBoardOnlineStateTrap for IAS SSMP V500R001C00.
                             Changed hwConfigChangeSN to hwConfigChangeIP and changed its type from Integer32 to IpAddress.
                             Changed the binding parameter hwConfigChangeSN of node hwDevUserlabelChangeTrap to hwConfigChangeIP.
                             Added the enumerated value of hwSysRegisterResponseStatus, namely nooperation(-1) (default value).
                             Added hwFrameTypeConfigured, hwActualSlotTypeName, hwOldDeviceIpAddr, hwNewDeviceIpAddr, 
                             hwOldSubslotType0, hwOldSubslotType1, hwOldSubslotType2, and hwOldSubslotType3;
                             Changed the binding parameter hwFrameTypeName of node hwDevFrameTypeInconsistentTrap to hwFrameTypeConfigured.
                             Changed the binding parameter hwSlotTypeName of node hwDevBoardMisMatchTrap to hwActualSlotTypeName.
                             Changed hwDevBoardFaltTrap to hwDevBoardFaultTrap.
                             Added the binding parameters hwSlotPrimaryStatus and hwSlotSecondaryStatus of node hwDevBoardDetectTrap.
                             Added the binding parameters hwSlotPrimaryStatus and hwSlotSecondaryStatus of node hwDevBoardStateChangedTrap.
                             Added the binding parameters hwSlotPrimaryStatus and hwSlotSecondaryStatus of node hwDevBoardStaChgOffLineTrap.
                             Added the binding parameters hwSubslotTypeName of node hwDevSubBoardMisMatchTrap."
                
                REVISION "201006070000Z"
                DESCRIPTION "V3.69, added hwSysVersionVrcb for NMS MIB adaptation."
                
                REVISION "201005100000Z"
                DESCRIPTION "V3.68, added hwSystemAdminStateMode,hwSystemAdminStatus and hwSystemPrimaryStatus in hwSystemPara.
                             Added hwSlotPrimaryStatus,hwSlotSecondaryStatus in hwSlotEntry.
                             Added hwSubslotPrimaryStatus,hwSubslotSecondaryStatus in hwSubslotEntry.
                             Added hwPortPrimaryStatus,hwPortSecondaryStatus in hwPortEntry."  
                
                REVISION "201004260000Z"
                DESCRIPTION "V3.67, implemented DT requirements and changed the syntax and semantics of SIMPLETEST."    
                
                REVISION "201004150000Z"
                DESCRIPTION "V3.66, added hwSysUpdateBoardVersion and hwSysUpdateBoardMaxTimeLen to hwSystemPara for board update." 
        
                REVISION "201004070000Z"
                DESCRIPTION "V3.65, changed the enumerated value of hwSlotNetworkRole.
                             Changed the MAX-ACCESS of hwFrameTypeName from accessible-for-notify to
                             read-only according to simpletest rules.
                             Changed the MAX-ACCESS of hwSubslotTypeName from accessible-for-notify to
                             read-only according to simpletest rules."
                             REVISION "201003310000Z"
                             DESCRIPTION "V3.64, added hwNatOnuTable, for querying the config information of ONU, and setting and querying 
                             the start IP address of the ONU IP address pool and the size of the pool."       
                
                REVISION "201003030000Z"
                DESCRIPTION "V3.63, implemented DT requirements and changed the syntax and semantics of SIMPLETEST." 
                
                REVISION "201003010000Z"
                DESCRIPTION "V3.62, added two MIB nodes for the OLT's managing the ONU through an agent. 
                             Supported configuring of the private network IP address and IP address range of the ONU." 
        
                REVISION "201002080000Z"
                DESCRIPTION "V3.61, modified this MIB according to DT requirements. The modifications are as follows:
                             1) Added hwFrameTypeName
                             2) Added hwSlotTypeName and updated the description.
                             3) Added hwSubslotTypeName.            
                             4) Deleted the following nodes:
                             hwFrameAdminResult
                             hwSlotAdminResult
                             hwSubslotAdminResult
                             hwPortAdminResult
                             hwDevGeneralTraps
                             hwFrameAdminResultTrap
                             hwSlotAdminResultTrap
                             hwSubSlotAdminResultTrap           
                             Certain nodes are changed to the following nodes:
                             hwTrapHardFaultPara1
                             hwTrapHardFaultPara2
                             hwTrapSystemRebootCause
                             hwTrapSystemRebootCause
                             hwTrapHardFaultLocation
                             hwConfigChangeSN
                             hwDevUserLabelType
                             hwDevUserLabel
                             hwDevVPI
                             hwDevVCI
                             hwDevVlanId
                             5) The following trap nodes are added:
                             hwDevBoardDetectTrap 
                             hwDevBoardDisappearedTrap 
                             hwDevBoardStateChangedTrap 
                             hwDevBoardStaChgOffLineTrap 
                             hwDevBoardAutoLoadTrap 
                             hwDevUserlabelChangeTrap 
                             hwDevSystemStartupTrap 
                             hwDevSystemDataSynCancelTrap 
                             hwDevActiveStandbyContolBoardInconsistentTrap 
                             hwDevSystemManualResetTrap 
                             hwDevFrameTypeInconsistentTrap 
                             hwDevBoardMisMatchTrap 
                             hwDevBoardHardFaultTrap 
                             hwDevBoardFaultTrap 
                             hwDevBoardRestoreTrap 
                             hwDevBoardReplacedTrap 
                             hwDevBoardEnterTemperatureProctectModeTrap 
                             hwDevBoardExitTemperatureProctectModeTrap 
                             hwDevBoardTemperatureTooHighTrap 
                             hwDevBoardTemperatureTooHighRecoverTrap 
                             hwDevBoardTemperatureTooLowTrap 
                             hwDevBoardTemperatureTooLowRecoverTrap 
                             hwDevPowerInputFaultTrap 
                             hwDevPowerInputRecoverTrap 
                             hwDevSubBoardTypeInconsistentTrap 
                             hwDevSubBoardMisMatchTrap 
                             hwDevSubBoardReplacedTrap 
                             hwDiagResOverloadFaultTrap 
                             hwDiagResOverloadRestoreTrap"  
                        
                REVISION "201001290000Z"                                                                    
                DESCRIPTION "V3.60, hwSlotNetworkRole is added."                                            
                                                                                    
                REVISION "201001260000Z"                                                                    
                DESCRIPTION "V3.59, Use SimpleTest clean warning and eror,Use MIB Browser clean             
                             warning and eror, Add MIB Description."                             
                                                                                    
                REVISION "200911300000Z"                                                                    
                DESCRIPTION "V3.58,  Board H802EDTB can act as PRA subscriber board,                        
                            provide CESoP broadband service,                                    
                            and carry TDM service. Add board working modes voice and satop."    
                                                                                    
                REVISION "200911040000Z"                                                                    
                DESCRIPTION "V3.57, For CR20090930022 requirement, add the table settings and the           
                            querying of the power supply modeof voice boards.                   
                            Add mib table hwPstnBoardCfgTable."                                 
                                                                                    
                REVISION "200910280000Z"                                                                    
                DESCRIPTION "V3.56, Add enumerated value mismatch (17) in leaf object hwSlotOperStatus."    
                                                                                    
                REVISION "200908310000Z"                                                                    
                DESCRIPTION "V3.53, Add enumerated values, namely, autoshutdown, hightempshutdown,          
                             and manualshutdown in leaf object hwSlotOperStatus."                
                                                                                    
                REVISION "200907240000Z"                                                                    
                DESCRIPTION "V3.52, Support globalized internal codes; support the setting                  
                             of system internal codes; add leaf object hwSysEncoding."           
                                                                                    
                REVISION "200906040000Z"                                                                    
                DESCRIPTION "V3.48, Add parameter configuration table of intelligent public telephone.      
                            This table supports the function of enabling intelligent            
                            public telephone, detection threshold of intelligent signals,       
                            gain and attenuation of intelligent signal on PCM side."            
                                                                                                                
                REVISION "200905310000Z"
                DESCRIPTION "V3.47, Add two objects for obtaining file names of currently used and 
                            unused patches(hwSysActivePatch and hwSysDeactivePatch) in table hwSystemPara. 
                            Add the locking of system configuration management plane. 
                            The original table is not archived, so new MIB table hwConfigLock is applied for."     
                
                REVISION "200905120000Z"
                DESCRIPTION "V3.46, Add an object of elabel CLEI in hwFrameTable."  
                
                REVISION "200901070000Z"
                DESCRIPTION "V3.41, Add the hwSysExchangeMode leaf object for obtaining system 
                             operating mode in MIB table hwSystemPara."    
                
                REVISION "200901040000Z"
                DESCRIPTION "V3.40, Modify the emumerated values of hwOntState leaf in hwAgentOnuInfoTable:
                             1. normal(0), 2. fault(1)."  
                
                REVISION "200812310000Z"
                DESCRIPTION "V3.39, Add ONT management function of OLT agent, add MIB table: 
                             ONT state table (hwAgentOntInfoTable); 
                             Add enumerated values of hwSlotAdminStatus leaf: poweron(12) and poweroff(13); 
                             Add enumerated value of hwSlotOperStatus leaf: shutdown(13)."   
                
                REVISION "200812010000Z"
                DESCRIPTION "V3.38, For the feature of optimizing in-service and out-of-service of boards,
                             add the processing for the timeout of in-service and out-of-service of boards, 
                             add hwSlotAdminForceOOSTimeoutWorkMode leaf object, 
                             and change the maximum time of board out-of service to one day.
                             For the feature of optimizing in-service and out-of-service of boards, 
                             add the two options, namely, enable users to select out-of-service 
                             immediately or in case of timeout; Add a hwSlotEndServiceMode leaf object;
                             and change the time of board out-of-service to 1-1440 minutes."   
                
                REVISION "200803170000Z"
                DESCRIPTION "V3.35, Put users in HUAWEI-MNGT-MIB and delete the descrption of three MIB tables, 
                             namely, hwCliUserParaTable,hwCliClientTable and hwCliSysPara."
                
                REVISION "200801300000Z"
                DESCRIPTION "V3.34, Modify table hwSystemPara: Add enumerated values (7-12) 
                             relevant to GMSAN in leaf hwSysWorkMode."  
        
                REVISION "200801220000Z"
                DESCRIPTION "V3.33, Modify hwRingAttrTable: Add an enumerated value in leaf hwRingacamplitude, 
                             namely,4, which indicates acamplitude75Vrms. 
                             Add the description of the first verstion that supports the feature."   
                
                REVISION "200712200000Z"
                DESCRIPTION "V3.32, Modify description of hwSlotTable. Add enumerated values of leaf 
                             hwSlotAdminStatus. Add two leaves hwSlotAdminForceOOSTime and hwSlotForceOOSTime."        
                
                REVISION "200710150000Z"
                DESCRIPTION "V3.31, (1) Add thresholds of high-tempreture alarm and low-tempreture alarm 
                             in system table hwSystemPara.
                             (2) Add board tempreture in table hwSlotEntry and add the port temperature 
                             query leaf in table hwPortEntry." 
                
                REVISION "200709240000Z"
                DESCRIPTION "V3.29,  Supplement the details about hwIopacketfile, hwSysWorkMode, 
                             and hwSysAverageBufferUsed."  
                
                REVISION "200706300000Z"
                DESCRIPTION "V3.26,  Update section 3.6 that descriebs the detailed specifications of 
                             the cascading relationship of hwFrameLinkTable."  
                
                REVISION "200706200000Z"
                DESCRIPTION "V3.25,  Add leaf object hwPortNetworkRole that describes the interface 
                             role in hwPortTable."    
                
                REVISION "200405280000Z"                                                                                                                                                                                                                                                
                DESCRIPTION "V3.03, Add auto-upgrade object."                                                                                                                                                                                                                       
                                                                                                                                                                                                                                                                                        
                REVISION "200402280000Z"                                                                                                                                                                                                                                                
                DESCRIPTION "V3.02,  Complete interface specifications                                                                                                                                                                                                              ."       
                                                                                                                                                                                                                                                                                        
                REVISION "200211290000Z"                                                                                                                                                                                                                                                
                DESCRIPTION "V2.00, Complete the draft."                                                                                                                                                                                                                        
    ::= { huaweiUtility 3 }

        -- 1.3.6.1.4.1.2011.6.3.1
        hwSystemPara OBJECT IDENTIFIER ::= { hwDev 1 }

        -- 1.3.6.1.4.1.2011.6.3.1.1
        hwSysIpAddr OBJECT-TYPE
            SYNTAX IpAddress
            MAX-ACCESS read-write
            STATUS current
            DESCRIPTION
                "
                IP address of the system.
                It'd better not to modify this address when out-band NMS is used.
                It will take no effect to separately configure IP address or IP address mask.
                "
            ::= { hwSystemPara 1 }


--  1.3.6.1.4.1.2011.6.3.1.2
        hwSysIpMask OBJECT-TYPE
            SYNTAX IpAddress
            MAX-ACCESS read-write
            STATUS current
            DESCRIPTION
                "
                IP address mask of the system.
                This object can take effect only when hwSysIpAddr is also set.
                "
            ::= { hwSystemPara 2 }


        -- 1.3.6.1.4.1.2011.6.3.1.3
        hwSysVersion OBJECT-TYPE
            SYNTAX DisplayString
            MAX-ACCESS read-only
            STATUS current
            DESCRIPTION
                "
                The system software version format is consistent with the
                specification of HUAWEI product.For example, MA5600V800R008C00.
                "
            ::= { hwSystemPara 3 }


        -- 1.3.6.1.4.1.2011.6.3.1.4
        hwSysTime OBJECT-TYPE
            SYNTAX DateAndTime
            MAX-ACCESS read-write
            STATUS current
            DESCRIPTION
                "
                This object is used for getting or setting current date and time of the system.
                "
            ::= { hwSystemPara 4 }


        -- 1.3.6.1.4.1.2011.6.3.1.5
        hwSysWorkMode OBJECT-TYPE
            SYNTAX INTEGER
                {
                amsanamsan(1),
                amsancmsan(2),
                cmsancmsan(3),
                cmsanamsan(4),
                amsanoffline(5),
                cmsanoffline(6),
                gmsangmsan(7),
                amsangmsan(8),
                gmsanamsan(9),
                cmsangmsan(10),
                gmsancmsan(11),
                gmsanoffline(12),
                null(65536)
                }
            MAX-ACCESS read-only
            STATUS current
            DESCRIPTION
                "
                This object is used for obtaining the working mode of the UA5000.
                Options:
                1. amsanamsan(1)     -indicates that the active and standby control boards are in position,
                                      with the active control board of AMSAN and the standby control board of AMSAN
                2. amsancmsan(2)     -indicates that the active and standby control boards are in position,
                                      with the active control board of AMSAN and the standby control board of CMSAN
                3. cmsancmsan(3)     -indicates that the active and standby control boards are in position,
                                      with the active control board of CMSAN and the standby control board of CMSAN
                4. cmsanamsan(4)     -indicates that the active and standby control boards are in position,
                                      with the active control board of CMSAN and the standby control board of AMSAN
                5. amsanoffline(5)   -indicates that the standby control board is not in position and the active
                                      control board is AMSAN
                6. cmsanoffline(6)   -indicates that the standby control board is not in position and the active
                                      control board is CMSAN
                7. gmsangmsan(7)     -indicates that the active and standby control boards are in position,
                                      with the active control board of GMSAN and the standby control board of GMSAN
                8: amsangmsan(8)     -indicates that the active and standby control boards are in position,
                                      with the active control board of AMSAN and the standby control board of GMSAN
                9. gmsanamsan(9)     -indicates that the active and standby control boards are in position,
                                      with the active control board of GMSAN and the standby control board of AMSAN
                10. cmsangmsan(10)   -indicates that the active and standby control boards are in position,
                                      with the active control board of CMSAN and the standby control board of GMSAN
                11. gmsancmsan(11)   -indicates that the active and standby control boards are in position,
                                      with the active control board of GMSAN and the standby control board of CMSAN
                12.gmsanoffline(12)  -indicates that the standby control board is not in position and the active
                                      control board is GMSAN
                13. null(65536)      -indicates that the system work mode is not set
                "
            ::= { hwSystemPara 5 }


        -- 1.3.6.1.4.1.2011.6.3.1.6
        hwSysAverageBufferUsed OBJECT-TYPE
            SYNTAX Integer32 (0..100)
            MAX-ACCESS read-only
            STATUS current
            DESCRIPTION
                "
                Query the average memory usage of the system.
                Collect the sum of the memory usage of all the boards that
                support memory query in the system, and then calculate the
                average value. The average value is the average memory usage of the system.
                "
            ::= { hwSystemPara 6 }


        -- 1.3.6.1.4.1.2011.6.3.1.7
        hwSysRsvedVlan OBJECT-TYPE
            SYNTAX Integer32 (2..4079)
            MAX-ACCESS read-only
            STATUS current
            DESCRIPTION
                "
                Describes the start VLAN ID of the reserved VLANs currently used by the system.
                Default: 4079
                The system automatically uses the 15 VLANs starting from the configured start VLAN ID as reserved VLANs.
                "
            ::= { hwSystemPara 7 }


        -- 1.3.6.1.4.1.2011.6.3.1.8
        hwSysRsvedVlanDb OBJECT-TYPE
            SYNTAX Integer32 (2..4079)
            MAX-ACCESS read-write
            STATUS current
            DESCRIPTION
                "
                Describes the start VLAN ID of the reserved VLANs configured in the system.
                The configuration takes effect after system restart.
                Range: 2-4079
                Default: 4079
                The system automatically uses the 15 VLANs starting from the configured start VLAN ID as reserved VLANs.

                VLANs 4094 and 4095 are fixedly reserved, and VLAN 1 is the native VLAN.
                Therefore, these three VLANs cannot be configured as the reserved VLANs.
                "
            ::= { hwSystemPara 8 }


        -- 1.3.6.1.4.1.2011.6.3.1.9
        hwIopacketVersion OBJECT-TYPE
            SYNTAX DisplayString
            MAX-ACCESS read-only
            STATUS current
            DESCRIPTION
                "
                The version information in the IO package, which is consistent
                with the system version information.
                "
            ::= { hwSystemPara 9 }


        -- 1.3.6.1.4.1.2011.6.3.1.10
        hwSysWorkScenario OBJECT-TYPE
            SYNTAX INTEGER
                {
                normal(1),
                upgrade(2)
                }
            MAX-ACCESS read-write
            STATUS current
            DESCRIPTION
                "
                System work scenario.
                    Used to identify whether the control board is in the upgrade(2)
                    or normal(1) scenario.
                    Options:
                    1. normal(1) -the normal scene of the system.
                                  If the device need not provide seamless upgrade, set the scenario to normal(1).
                                  If the scenario is changed from upgrade(2) to normal(1) and the standby control
                                  board is in position, reset the standby control board.
                    2. upgrade(2)-the upgrade scene of the system.
                                  When the device needs to provide seamless upgrade,
                                  that is, the service is not interrupted during upgrade, set the scenario to upgrade(2).
                                  If it is set to upgrade(2), you can perform operations related to upgrade only,
                                  such as saving, loading, backup, active/standby switchover, system reset, and query.
                "
            ::= { hwSystemPara 10 }


        -- 1.3.6.1.4.1.2011.6.3.1.11
        hwSysTemperatureHighThreshold OBJECT-TYPE
            SYNTAX Integer32
            MAX-ACCESS read-write
            STATUS current
            DESCRIPTION
                "
                The threshold of the system.
                When you set a high temperature threshold, you also need to set a low temperature threshold.
                Range:40~105
                The invalid value is 65535.If the threshold is not configured,the invalid value will be returned.
                "
            ::= { hwSystemPara 11 }


        -- 1.3.6.1.4.1.2011.6.3.1.12
        hwSysTemperatureLowThreshold OBJECT-TYPE
            SYNTAX Integer32
            MAX-ACCESS read-write
            STATUS current
            DESCRIPTION
                "
                The threshold of the system.
                When you set a low temperature threshold, you also need to set a high temperature threshold.
                Range:-40~20
                The invalid value is 65535.If the threshold is not configured,the invalid value will be returned.
                "
            ::= { hwSystemPara 12 }


        -- 1.3.6.1.4.1.2011.6.3.1.13
        hwSysExchangeMode OBJECT-TYPE
            SYNTAX INTEGER
                {
                backup(1),
                loadSharing(2),
                null(65536)
                }
            MAX-ACCESS read-only
            STATUS current
            DESCRIPTION
                "
                System Exchange-Mode,
                Options:
                    1. backup(1)       -indicates active/standby mode. Two control boards serve as the active and standby control
                                        boards respectively. The switching chip of the active control board works independently
                    2. loadSharing(2) -indicates load sharing mode. The switching chips of the two control boards work
                                        together to share the traffic
                    3. null(65536)     -indicates system exchange mode is not set
                    "
            ::= { hwSystemPara 13 }


        -- 1.3.6.1.4.1.2011.6.3.1.14
        hwSysActivePatch OBJECT-TYPE
            SYNTAX OCTET STRING
            MAX-ACCESS read-only
            STATUS current
            DESCRIPTION
                "
                Display the information of the active patches in current system.
                "
            ::= { hwSystemPara 14 }


        -- 1.3.6.1.4.1.2011.6.3.1.15
        hwSysDeactivePatch OBJECT-TYPE
            SYNTAX OCTET STRING
            MAX-ACCESS read-only
            STATUS current
            DESCRIPTION
                "
                This object is used for querying the information about the deactivated patch in the current system.
                "
            ::= { hwSystemPara 15 }


        -- 1.3.6.1.4.1.2011.6.3.1.16
        hwSystemAutoConfigStatus OBJECT-TYPE
            SYNTAX INTEGER
                {
                enable(1),
                disable(2)
                }
            MAX-ACCESS read-write
            STATUS current
            DESCRIPTION
                "
                GE uplink software commissioning free configuration.
                Options:
                1.enable(1)  -the default value is enable
                2.disable(2) -this object is no longer used
                "
            ::= { hwSystemPara 16 }


        -- 1.3.6.1.4.1.2011.6.3.1.17
        hwSystemEnergySavingSwitch OBJECT-TYPE
            SYNTAX INTEGER
                {
                basic(1),
                deep(2),
                optimal(3),
                standard(4)
                }
            MAX-ACCESS read-write
            STATUS current
            DESCRIPTION
                "
                The energy-saving mode of system.
                Options:
                1.basic(1) -when it is set to basic(1), the system energy saving mode is basic mode.
                2.deep(2) -when it is set to deep(2), the system energy saving mode is deep mode.
                3.optimal(3) -when it is set to optimal(3), the system energy saving mode is optimal mode.
                4.standard(4) -when it is set to standard(4), the system energy saving mode is standard mode.
                The default value is basic(1).
                "
            ::= { hwSystemPara 17 }


        -- 1.3.6.1.4.1.2011.6.3.1.18
        hwSysEncoding OBJECT-TYPE
            SYNTAX INTEGER
                {
                default(1),
                gbk(2),
                iso88591(3),
                utf8(4)
                }
            MAX-ACCESS read-write
            STATUS current
            DESCRIPTION
                "
                The encoding mode of characters in the system.
                Options:
                1. default(1)   -indicates that the encoding mode is no set
                2. gbk(2)       -indicates that the encoding mode of characters is gbk
                3. iso88591(3) -indicates that the encoding mode of characters is iso8859-1
                4. utf8(4)     -indicates that the encoding mode of characters is utf-8
                The value can be gbk(2), iso8859-1(3), or utf-8(4).
                Default: 1
                "
            ::= { hwSystemPara 18 }


        -- 1.3.6.1.4.1.2011.6.3.1.19
        hwSysUpdateBoardVersion OBJECT-TYPE
            SYNTAX INTEGER { updateBoardVersion(1) }
            MAX-ACCESS read-write
            STATUS current
            DESCRIPTION
                "
                Update Board Version
                Options:
                1.updateBoardVersion(1) -set operation only
                "
            ::= { hwSystemPara 19 }


        -- 1.3.6.1.4.1.2011.6.3.1.20
        hwSysUpdateBoardMaxTimeLen OBJECT-TYPE
            SYNTAX Integer32 (1..24)
            MAX-ACCESS read-write
            STATUS current
            DESCRIPTION
                "
                Update Board Version Max Time Len
                "
            ::= { hwSystemPara 20 }


        -- 1.3.6.1.4.1.2011.6.3.1.21
        hwSystemAdminStateMode OBJECT-TYPE
            SYNTAX INTEGER
                {
                grStandard(1),
                private(2)
                }
            MAX-ACCESS read-write
            STATUS current
            DESCRIPTION
                "System admin state mode.
                DEFVAL { private }
                Options:
                1.grStandard(1)   -grStandard mode complies with GR series standard(such as GR-1093, used in North America).
                2.private(2)       -private mode,Huawei devices support.
                "
            ::= { hwSystemPara 21 }


        -- 1.3.6.1.4.1.2011.6.3.1.22
        hwSystemAdminStatus OBJECT-TYPE
            SYNTAX INTEGER
                {
                nooperation(-1),
                is(1),
                oos(2)
                }
            MAX-ACCESS read-write
            STATUS current
            DESCRIPTION
                "
                The system admin status.
                Options:
                1. nooperation(-1) -default state of the system.
                2. is(1)           -in service
                3. oos(2)          -out of service
                "
            ::= { hwSystemPara 22 }


        -- 1.3.6.1.4.1.2011.6.3.1.23
        hwSystemPrimaryStatus OBJECT-TYPE
            SYNTAX INTEGER
                {
                isNr(1),
                isAnr(2),
                isRst(3),
                isAnrst(4),
                oosAu(5),
                oosMa(6),
                oosAuma(7),
                oosAurst(8),
                oosMaanr(9)
                }
            MAX-ACCESS read-only
            STATUS current
            DESCRIPTION
                "
                The system primary status.
                Options:
                1. isNr(1)     -in Service, normal
                2. isAnr(2)    -in service, abnormal
                3. isRst(3)    -in service, restricted
                4. isAnrst(4)  -in service, abnormal & restricted
                5. oosAu(5)    -out of service, autonomous
                6. oosMa(6)    -out of service, management
                7. oosAuma(7)  -out of service, autonomous & management
                8. oosAurst(8) -out of service, autonomous & restricted
                9. oosMaanr(9) -out of service, management & abnormal
                "
            ::= { hwSystemPara 23 }


        -- 1.3.6.1.4.1.2011.6.3.1.24
        hwDeviceArchType OBJECT-TYPE
            SYNTAX INTEGER
                {
                arch1(1),
                arch2(2),
                arch3(3)
                }
            MAX-ACCESS read-only
            STATUS current
            DESCRIPTION
                "
                The hardware structure type of a device.
                Currently, the hardware structure types of the existing versions are as follows:
                Options:
                1.arch1(1)  -in MxUV8R305, the hardware structure type of the MA5620E, MA5620G, MA5626E, MA5626G, and MA5651(G) is arch1(1)
                             In MxUV8R306, hardware structure type of the MA5610 is arch1(1)
                             In MxUV8R307, hardware structure type of the MA5612, MA5620, and MA5626 is arch1(1)
                2.arch2(2)  -in MxUV8R306, the  hardware structure type of the MA5616 and MA5652(G) is arch2(2)
                3.arch3(3)  -in MxUV8R308, hardware structure type of the MA5612, MA5620, MA5626, and MA5616 is arch3(3)
                         "
            ::= { hwSystemPara 24 }


        -- 1.3.6.1.4.1.2011.6.3.1.25
        hwUplinkSysIPAddr OBJECT-TYPE
            SYNTAX IpAddress
            MAX-ACCESS read-write
            STATUS current
            DESCRIPTION
                "
                The IP address of the uplink system of PVM, it is only used when PVM worked in integrated mode
                and the IPM worked as the uplink board.
                "
            ::= { hwSystemPara 25 }


        -- 1.3.6.1.4.1.2011.6.3.1.26
        hwSysMainBoardTypeDesc OBJECT-TYPE
            SYNTAX OCTET STRING (SIZE (0..64))
            MAX-ACCESS read-only
            STATUS current
            DESCRIPTION
                "
                The mainboard description.
                "
            ::= { hwSystemPara 26 }


        -- 1.3.6.1.4.1.2011.6.3.1.27
        hwSysEnergySaving OBJECT-TYPE
            SYNTAX BITS
                {
             esEnergySavingService(0),
             esBoardAutoPowerOnOff(1),
             esPlatform(2), 
             esVector(3),   
             esOpticalAccess(4),
             esCopperAccess(5),
             esInnovation(6)
                }
            MAX-ACCESS read-write
            STATUS current
            DESCRIPTION
                "
                The automatic energy saving function consists of seven sub-functions, which are indicated by bits .All bits are disabled by default. If
                a bit is 0, the represented function is disabled.if a bit is 1, the represented function is enabled.This function is independent of the
                energy saving function of the optical line terminal (OLT) products by powering off boards.
                The energy saving bits flag:
                1. esEnergySavingService(0)  - indicates energy-saving-service-related features, include the feature of automatically unbinding
                                    an extended profile.
                2. esBoardAutoPowerOnOff(1)  - indicates automatic power-off features on a board for energy saving, include the automatic
                                    power-on and power-off feature on a board.
                3. esPlatform(2)             - indicates platform-related energy saving features, include energy saving on the
                                    control board and upstream board.
                4. esVector(3)               - indicates vectoring-related energy saving features, include vectoring disabling feature.
                5. esOpticalAccess(4)        - indicates the optical access-related energy saving feature,and this object is reserved .
                6. esCopperAccess(5)         - indicates copper-access-related energy saving features,include MELT energy saving feature.
                7. esInnovation(6)           - indicates HuaWei's proprietary energy saving technologies,include the line driver(LD)
                                    energy saving feature.
                "
            ::= { hwSystemPara 27 }


        -- 1.3.6.1.4.1.2011.6.3.1.28
        hwSysSceneMode OBJECT-TYPE
            SYNTAX INTEGER
                {
                olt(1),
                msan(3)
                }
            MAX-ACCESS read-only
            STATUS current
            DESCRIPTION
                "
                The device work scene.
                Options:
                1. olt(1)     -work in OLT scene
                2. msan(3)    -work in MSAN scene
                "
            ::= { hwSystemPara 28 }


        -- 1.3.6.1.4.1.2011.6.3.1.29
        hwSysFtpXmlConfigure OBJECT-TYPE
            SYNTAX INTEGER
                {
                useful(1),
                useless(2)
                }
            MAX-ACCESS read-only
            STATUS current
            DESCRIPTION
                "
                The state of XML file.
                Options:
                1. useful(1)     -Xml file is useful
                2. useless(2)   -Xml file is useless
                "
            ::= { hwSystemPara 29 }


        -- 1.3.6.1.4.1.2011.6.3.1.30
        hwSysCentralizedMgmtPrimary OBJECT-TYPE
            SYNTAX INTEGER
                {
                extendFrame(1),
                standAlone(2)
                }
            MAX-ACCESS read-write
            STATUS current
            DESCRIPTION
                "
                The primary mode for centralized management.
                Options:
                1. extendFrame(1)  -Extended frame management
                2. standAlone(2)   -Stand alone management
                "
            ::= { hwSystemPara 30 }


        -- 1.3.6.1.4.1.2011.6.3.1.31
        hwUpgradeVerifyVersion OBJECT-TYPE
            SYNTAX DisplayString
            MAX-ACCESS read-only
            STATUS current
            DESCRIPTION
                "
                The system software version used in update scene for HUAWEI product.For example, MA5600V800R008C00.
                "
            ::= { hwSystemPara 31 }
            
        -- 1.3.6.1.4.1.2011.6.3.3.1.32
        hwDevLongitude OBJECT-TYPE
            SYNTAX Integer32 (-18000000..18000000 | 2147483647)
            MAX-ACCESS read-write
            STATUS current
            DESCRIPTION
                "
                The longitude of the device.
                The value expands 100000 times and the value 2147483647 indicates invalid longitude.
                "
            ::= { hwSystemPara 32 }
            
        -- 1.3.6.1.4.1.2011.6.3.3.1.33
        hwDevLatitude OBJECT-TYPE
            SYNTAX Integer32 (-9000000..9000000 | 2147483647)
            MAX-ACCESS read-write
            STATUS current
            DESCRIPTION
                "
                The latitude of the device.
                The value expands 100000 times and the value 2147483647 indicates invalid latitude.
                "
            ::= { hwSystemPara 33 }
            
        -- 1.3.6.1.4.1.2011.6.3.3.1.34
        hwDevElevation OBJECT-TYPE
            SYNTAX Integer32 (-32768..32767)
            MAX-ACCESS read-write
            STATUS current
            DESCRIPTION
                "
                The elevation of the device, in unit of meters.
                The value 32767 indicates invalid elevation.
                "
            ::= { hwSystemPara 34 }
            
        -- 1.3.6.1.4.1.2011.6.3.3.1.35
        hwDevHorizontalErr OBJECT-TYPE
            SYNTAX Unsigned32 (0..65535 | 4294967295)
            MAX-ACCESS read-write
            STATUS current
            DESCRIPTION
                "
                The horizontal error of the device, in unit of meters.
                The value 4294967295 indicates invalid horizontal error.
                "
            ::= { hwSystemPara 35 }
            
        -- 1.3.6.1.4.1.2011.6.3.3.1.36
        hwDevAltitudeErr OBJECT-TYPE
            SYNTAX Unsigned32 (0..65535 | 4294967295)
            MAX-ACCESS read-write
            STATUS current
            DESCRIPTION
                "
                The altitude error of the device, in unit of meters.
                The value 4294967295 indicates invalid altitude error.
                "
            ::= { hwSystemPara 36 }
            
        -- 1.3.6.1.4.1.2011.6.3.3.1.37
        hwDevAreaCode OBJECT-TYPE
            SYNTAX OCTET STRING (SIZE (0 | 12))
            MAX-ACCESS read-write
            STATUS current
            DESCRIPTION
                "
                The area code of the device.
                The length of area code is 12. The characters can be 0, 1, 2, 3, 4, 5, 6, 7, 8 and 9.
                The zero-length string indicates invalid area code.
                "
            ::= { hwSystemPara 37 }
            
        -- 1.3.6.1.4.1.2011.6.3.3.1.38
        hwDevGisTimeStamp OBJECT-TYPE
            SYNTAX Unsigned32 (0..4294967295)
            MAX-ACCESS read-write
            STATUS current
            DESCRIPTION
                "
                The time stamp of the measurement signature, which is the number of seconds from 00:00 on January 1, 1970 to the current time.
                The value 4294967295 indicates invalid time stamp.
                "
            ::= { hwSystemPara 38 }
            
        -- 1.3.6.1.4.1.2011.6.3.3.1.39
        hwDevGisDigest OBJECT-TYPE
            SYNTAX OCTET STRING (SIZE (0 | 16))
            MAX-ACCESS read-write
            STATUS current
            DESCRIPTION
                "
                The check value of the measurement signature.
                The length of check value is 16. The characters can be 0, 1, 2, 3, 4, 5, 6, 7, 8, 9, A, B, C, D, E and F.
                The zero-length string indicates invalid check value.
                "
            ::= { hwSystemPara 39 }
            
        -- 1.3.6.1.4.1.2011.6.3.3.1.40
        hwDevGisCheckCode OBJECT-TYPE
            SYNTAX OCTET STRING (SIZE (0 | 4))
            MAX-ACCESS read-write
            STATUS current
            DESCRIPTION
                "
                The check code of the device GPS information.
                The length of check code is 4. The characters can be 0, 1, 2, 3, 4, 5, 6, 7, 8, 9, A, B, C, D, E and F.
                The zero-length string indicates invalid area check code.
                "
            ::= { hwSystemPara 40 }
            
        -- 1.3.6.1.4.1.2011.6.3.1.41
        hwSysSsdSwitch OBJECT-TYPE
            SYNTAX INTEGER
                {
                enable(1),
                disable(2)
                }
            MAX-ACCESS read-write
            STATUS current
            DESCRIPTION
                "
                The secure software downloading status.
                Options:
                1. enable(1)     -The secure software downloading is enable
                2. disable(2)    -The secure software downloading is disable
                "
            ::= { hwSystemPara 41 }
            
        -- 1.3.6.1.4.1.2011.6.3.1.42
        hwSysFtpMode OBJECT-TYPE
            SYNTAX INTEGER
                {
                port(1),
                passive(2)
                }
            MAX-ACCESS read-write
            STATUS current
            DESCRIPTION
                "
                FTP connection mode.
                Options:
                1. port(1)       -Set the FTP connection mode to port.
                2. passive(2)    -Set the FTP connection mode to passive.
                Default: port(1)
                "
            ::= { hwSystemPara 42 }

        -- 1.3.6.1.4.1.2011.6.3.1.43
        hwSysMarketScene OBJECT-TYPE
            SYNTAX INTEGER
                {
                carrier(1),
                enterprise(2)
                }
            MAX-ACCESS read-only
            STATUS current
            DESCRIPTION
                "
                The device options:
				1. carrier(1) -Device work in carrier scene.
				2. enterprise(2) -Device work in enterprise scene.
				Default: carrier(1)
                "
            ::= { hwSystemPara 43 }			
			
        -- 1.3.6.1.4.1.2011.6.3.1.999
        hwSysVersionVrcb OBJECT-TYPE
            SYNTAX DisplayString
            MAX-ACCESS read-only
            STATUS current
            DESCRIPTION
                "
                The device MIB build version, used by NMS for MIB adaption.
                "
            ::= { hwSystemPara 999 }


        -- 1.3.6.1.4.1.2011.6.3.2
        hwNmsParaTable OBJECT-TYPE
            SYNTAX SEQUENCE OF HwNmsParaEntry
            MAX-ACCESS not-accessible
            STATUS current
            DESCRIPTION
                "
                The index of this table is hwNmsIndex.
                NMS parameters configuration table.
                This table is no longer used.
                "
            ::= { hwDev 2 }


        -- 1.3.6.1.4.1.2011.6.3.2.1
        hwNmsParaEntry OBJECT-TYPE
            SYNTAX HwNmsParaEntry
            MAX-ACCESS not-accessible
            STATUS current
            DESCRIPTION
                "
                The index of this entry is hwNmsIndex.
                NMS parameters configuration table.
                This table is no longer used.
                "
            INDEX { hwNmsIndex }
            ::= { hwNmsParaTable 1 }


        HwNmsParaEntry ::=
            SEQUENCE {
                hwNmsIndex
                    Integer32,
                hwNmsName
                    OCTET STRING,
                hwNmsIp
                    IpAddress,
                hwNmsMask
                    IpAddress,
                hwNmsMaintainMode
                    INTEGER,
                hwNmsGetCommunity
                    OCTET STRING,
                hwNmsSetCommunity
                    OCTET STRING,
                hwNmsSnmpPort
                    Integer32,
                hwNmsTrapPort
                    Integer32,
                hwNmsClass
                    INTEGER,
                hwNmsStatus
                    RowStatus
             }

        -- 1.3.6.1.4.1.2011.6.3.2.1.1
        hwNmsIndex OBJECT-TYPE
            SYNTAX Integer32 (1..32)
            MAX-ACCESS read-only
            STATUS current
            DESCRIPTION
                "
                Index(1..32),at most supports 32 NMSs, exclusively identifies an NMS.
                This object is no longer used.
                "
            ::= { hwNmsParaEntry 1 }


        -- 1.3.6.1.4.1.2011.6.3.2.1.2
        hwNmsName OBJECT-TYPE
            SYNTAX OCTET STRING (SIZE (0..63))
            MAX-ACCESS read-write
            STATUS current
            DESCRIPTION
                "
                Name of the NMS, which does not have to be consistent with that of the NMS workstation.
                This object is no longer used.
                "
            ::= { hwNmsParaEntry 2 }


        -- 1.3.6.1.4.1.2011.6.3.2.1.3
        hwNmsIp OBJECT-TYPE
            SYNTAX IpAddress
            MAX-ACCESS read-write
            STATUS current
            DESCRIPTION
                "
                IP address of the NMS workstation that can be outband or inband address.
                This object is no longer used.
                "
            ::= { hwNmsParaEntry 3 }


        -- 1.3.6.1.4.1.2011.6.3.2.1.4
        hwNmsMask OBJECT-TYPE
            SYNTAX IpAddress
            MAX-ACCESS read-write
            STATUS deprecated
            DESCRIPTION
                "
                IP address mask of the NMS workstation.
                This object is no longer used.
                "
            ::= { hwNmsParaEntry 4 }


        -- 1.3.6.1.4.1.2011.6.3.2.1.5
        hwNmsMaintainMode OBJECT-TYPE
            SYNTAX INTEGER
                {
                inBandwidth(1),
                outBandwidth(2)
                }
            MAX-ACCESS read-write
            STATUS deprecated
            DESCRIPTION
                "
                Maintenance mode of NMS workstation. If the IP address
                of the NMS station is in-band, the mode must also be in-band.
                This object is no longer used.
                Options:
                1.inBandwidth(1)  -in Bandwidth
                2.outBandwidth(2) -out Bandwidth
                "
            ::= { hwNmsParaEntry 5 }


        -- 1.3.6.1.4.1.2011.6.3.2.1.6
        hwNmsGetCommunity OBJECT-TYPE
            SYNTAX OCTET STRING (SIZE (0..31))
            MAX-ACCESS read-write
            STATUS current
            DESCRIPTION
                "
                Community authentication name used for SNMP
                protocol GET operation, default value: public.
                This object is no longer used.
                "
            ::= { hwNmsParaEntry 6 }


        -- 1.3.6.1.4.1.2011.6.3.2.1.7
        hwNmsSetCommunity OBJECT-TYPE
            SYNTAX OCTET STRING (SIZE (0..31))
            MAX-ACCESS read-write
            STATUS current
            DESCRIPTION
                "
                Community authentication name used for SNMP
                protocol SET operation, default value: private.
                This object is no longer used.
                "
            ::= { hwNmsParaEntry 7 }


        -- 1.3.6.1.4.1.2011.6.3.2.1.8
        hwNmsSnmpPort OBJECT-TYPE
            SYNTAX Integer32
            MAX-ACCESS read-write
            STATUS deprecated
            DESCRIPTION
                "
                Snmp communication port of NMS workstation,default value:161.
                This object is no longer used.
                "
            ::= { hwNmsParaEntry 8 }


        -- 1.3.6.1.4.1.2011.6.3.2.1.9
        hwNmsTrapPort OBJECT-TYPE
            SYNTAX Integer32
            MAX-ACCESS read-write
            STATUS deprecated
            DESCRIPTION
                "
                Trap receive Port of NMS workstation, default value:162.
                This object is no longer used.
                "
            ::= { hwNmsParaEntry 9 }


        -- 1.3.6.1.4.1.2011.6.3.2.1.10
        hwNmsClass OBJECT-TYPE
            SYNTAX INTEGER
                {
                ro(1),
                rw(2),
                rwWithTrap(3),
                trapOnly(4)
                }
            MAX-ACCESS read-write
            STATUS deprecated
            DESCRIPTION
                "
                Class of NMS station,default value is 3.
                This object is no longer used.
                Options:
                1.ro(1)          - read only
                2.rw(2)          - read write
                3.rwWithTrap(3)  - default value, read write with trap
                4.trapOnly(4)    - only with trap
                "
            ::= { hwNmsParaEntry 10 }


        -- 1.3.6.1.4.1.2011.6.3.2.1.11
        hwNmsStatus OBJECT-TYPE
            SYNTAX RowStatus
            MAX-ACCESS read-create
            STATUS current
            DESCRIPTION
                "
                Operation status of NMS station. The NMS station
                can be added,deleted and modified.
                This object is no longer used.
                "
            ::= { hwNmsParaEntry 11 }


        -- 1.3.6.1.4.1.2011.6.3.3
        hwSlotConf OBJECT IDENTIFIER ::= { hwDev 3 }


        -- 1.3.6.1.4.1.2011.6.3.3.1
        hwFrameTable OBJECT-TYPE
            SYNTAX SEQUENCE OF HwFrameEntry
            MAX-ACCESS not-accessible
            STATUS current
            DESCRIPTION
                "
                The index of this table is hwFrameTable.
                Shelf description table that describes basic information of a shelf.
                You can obtain the shelf information, including the shelf type,
                number of slots, and the shelf running status, and the shelf management status.
                "
            ::= { hwSlotConf 1 }


        -- 1.3.6.1.4.1.2011.6.3.3.1.1
        hwFrameEntry OBJECT-TYPE
            SYNTAX HwFrameEntry
            MAX-ACCESS not-accessible
            STATUS current
            DESCRIPTION
                "
                The index of this entry is hwFrameTable.
                Shelf description table that describes basic information of a shelf.
                You can obtain the shelf information, including the shelf type,
                number of slots, and the shelf running status, and the shelf management status.
                "
            INDEX { hwFrameIndex }
            ::= { hwFrameTable 1 }


        HwFrameEntry ::=
            SEQUENCE {
                hwFrameIndex
                    Integer32,
                hwFrameType
                    HWFrameType,
                hwFrameDesc
                    OCTET STRING,
                hwSlots
                    Integer32,
                hwFrameOperStatus
                    INTEGER,
                hwFrameAdminStatus
                    INTEGER,
                hwFrameRowStatus
                    RowStatus,
                hwBackplaneVersion
                    OCTET STRING,
                hwBackplanePhySerialNum
                    OCTET STRING,                
                hwFrameResetTimeout
                    Integer32,
                hwFrameCLEICode
                    OCTET STRING,
                hwFrameTypeName
                    OCTET STRING,
                hwFrameExtendPort
                    Integer32,
                hwFrameUplinkPort
                    Integer32,
                hwFrameRackID
                    Integer32,
                hwFrameExtendingSubId
                    Integer32,
                hwFrameExtendType
                    Integer32,
                hwFrameHardwareDesc
                    OCTET STRING,
                hwFrameGponDeviceSn
                    OCTET STRING,
                hwFramePhySerialNum
                    OCTET STRING,
                hwFrameQueryAssit
                    Integer32
             }

        -- 1.3.6.1.4.1.2011.6.3.3.1.1.1
        hwFrameIndex OBJECT-TYPE
            SYNTAX Integer32 (0..1024)
            MAX-ACCESS read-only
            STATUS current
            DESCRIPTION
                "
                The index of a shelf in the device.
                "
            ::= { hwFrameEntry 1 }


        -- 1.3.6.1.4.1.2011.6.3.3.1.1.2
        hwFrameType OBJECT-TYPE
            SYNTAX HWFrameType
            MAX-ACCESS read-create
            STATUS current
            DESCRIPTION
                "
                The type of a shelf, which can be obtained from HUAWEI-TC-MIB.mib.
                "
            ::= { hwFrameEntry 2 }


        -- 1.3.6.1.4.1.2011.6.3.3.1.1.3
        hwFrameDesc OBJECT-TYPE
            SYNTAX OCTET STRING (SIZE (0..128))
            MAX-ACCESS read-create
            STATUS current
            DESCRIPTION
                "
                The description about the frame.
                It is used to describe some extra information.
                For convenient management, you can set the location of the room in
                which the shelf is located as the description.
                "
            ::= { hwFrameEntry 3 }


        -- 1.3.6.1.4.1.2011.6.3.3.1.1.4
        hwSlots OBJECT-TYPE
            SYNTAX Integer32
            MAX-ACCESS read-only
            STATUS current
            DESCRIPTION
                "
                The number of physical slots in the shelf.
                "
            ::= { hwFrameEntry 4 }


        -- 1.3.6.1.4.1.2011.6.3.3.1.1.5
        hwFrameOperStatus OBJECT-TYPE
            SYNTAX INTEGER
                {
                normal(1),
                fault(2),
                other(3),
                discovery(4),
                mismatch(5),
                offline(6)
                }
            MAX-ACCESS read-only
            STATUS current
            DESCRIPTION
                "
                The operation status of frame.
                Options:
                1. normal(1)   -indicates that the shelf is running normally
                2. fault(2)    -indicates that the shelf is faulty
                3. other(3)    -indicates that the shelf is in a state other than the previous three states
                4. discovery(4)-indicates that the shelf is in the auto discovery state and is to be activated
                5. mismatch(5) -indicates that the shelf type is inconsistent with the configuration in the database of device
                6. offline(6)  -indicates that the shelf is offline or the link of the shelf is down
                "
            ::= { hwFrameEntry 5 }


        -- 1.3.6.1.4.1.2011.6.3.3.1.1.6
        hwFrameAdminStatus OBJECT-TYPE
            SYNTAX INTEGER
                {
                nooperation(-1),
                disable(1),
                enable(2),
                reset(3),
                test(4),
                confirm(5),
                delete(6),
                batchconfirm(7),
                bind(8)
                }
            MAX-ACCESS read-create
            STATUS current
            DESCRIPTION
                "
                The administration status of frame.
                Options:
                1. nooperation(-1) -  default state of the system
                2. disable(1)      -  indicates that the frame administration state is disable
                3. enable(2)       -  indicates that the frame administration state is enable
                4. reset(3)        -  reset the shelf. If you need to reset the shelf immediately,
                                      perform the operation only. If you need to reset the shelf after a certain period,
                                      you also need to set hwFrameResetTimeout.
                                      If you need to reset the control shelf, the entire system is reset;
                                      otherwise, the control board in the specified shelf is reset
                5. test(4)         -  test the frame
                6. confirm(5)      -  confirm the frame
                7. delete(6)       -  delete the frame info
                8. batchconfirm(7) -  confirm the boards in a shelf in batches
                9. bind(8)         -  bind ont serial number with the extended frame ID
                "
            ::= { hwFrameEntry 6 }


        -- 1.3.6.1.4.1.2011.6.3.3.1.1.7
        hwFrameRowStatus OBJECT-TYPE
            SYNTAX RowStatus
            MAX-ACCESS read-create
            STATUS current
            DESCRIPTION
                "
                The device that supports the slave shelf allows you to add a shelf (createAndGo(4))
                and delete a shelf (destroy(6)) only.
                The device that does not support the slave shelf and does not support the setting operation.
                "
            ::= { hwFrameEntry 7 }


        -- 1.3.6.1.4.1.2011.6.3.3.1.1.8
        hwBackplaneVersion OBJECT-TYPE
            SYNTAX OCTET STRING (SIZE (0..255))
            MAX-ACCESS read-only
            STATUS current
            DESCRIPTION
                "
                Backplane board version information.
                Use the new-line character \n (ACSII 0x0A)
                to space various version information.
                It mainly contains the following information:
                Hardware PCB version \n
                MAB version \n
                Board Type \n
                "
            ::= { hwFrameEntry 8 }


        -- 1.3.6.1.4.1.2011.6.3.3.1.1.9
        hwBackplanePhySerialNum OBJECT-TYPE
            SYNTAX OCTET STRING (SIZE (0..32))
            MAX-ACCESS read-only
            STATUS current
            DESCRIPTION
                "
                The vendor-specific serial number string for the physical entity.
                The preferred value is the serial number string actually printed
                on the component itself.
                "
            ::= { hwFrameEntry 9 }


        -- 1.3.6.1.4.1.2011.6.3.3.1.1.10
        hwFrameResetTimeout OBJECT-TYPE
            SYNTAX Integer32 (-1 | 2..600)
            MAX-ACCESS read-write
            STATUS current
            DESCRIPTION
                "
                Used to set the delay time of shelf reset, in unit of seconds.
                When you set hwFrameResetTimeout, you also need to set hwFrameAdminStatus to reset(3).
                If the shelf resetting fails, the device tries again in three seconds,
                until the resetting is successful or the number of resetting attempts exceeds the maximum.
                Initial value is -1.
                "
            ::= { hwFrameEntry 10 }


--  1.3.6.1.4.1.2011.6.3.3.1.1.11
        -- 1.3.6.1.4.1.2011.6.3.3.1.1.11
        hwFrameCLEICode OBJECT-TYPE
            SYNTAX OCTET STRING (SIZE (0..640))
            MAX-ACCESS read-only
            STATUS current
            DESCRIPTION
                "
                Frame CLEI Code (COMMON LANGUAGE Location Identifier Code):
                Used to identify the location and the type of a telecommunication device.
                For the definition of the CLEI Code, refer to the GR-485.
                "
            ::= { hwFrameEntry 11 }


        -- 1.3.6.1.4.1.2011.6.3.3.1.1.12
        hwFrameTypeName OBJECT-TYPE
            SYNTAX OCTET STRING
            MAX-ACCESS read-only
            STATUS current
            DESCRIPTION
                "
                Frame information description, to describe name information of the frame.
                "
            ::= { hwFrameEntry 12 }


        -- 1.3.6.1.4.1.2011.6.3.3.1.1.13
        hwFrameExtendPort OBJECT-TYPE
            SYNTAX Integer32
            MAX-ACCESS read-write
            STATUS current
            DESCRIPTION
                "
                The extending port of main frame which is used to connect extended frame.
                "
            ::= { hwFrameEntry 13 }


        -- 1.3.6.1.4.1.2011.6.3.3.1.1.14
        hwFrameUplinkPort OBJECT-TYPE
            SYNTAX Integer32
            MAX-ACCESS read-only
            STATUS current
            DESCRIPTION
                "
                The uplink port of extended frame.
                "
            ::= { hwFrameEntry 14 }


        -- 1.3.6.1.4.1.2011.6.3.3.1.1.15
        hwFrameRackID OBJECT-TYPE
            SYNTAX Integer32 (0..65535)
            MAX-ACCESS read-write
            STATUS current
            DESCRIPTION
                "
                Indicates the ID of the rack.
                "
            ::= { hwFrameEntry 15 }


        -- 1.3.6.1.4.1.2011.6.3.3.1.1.16
        hwFrameExtendingSubId OBJECT-TYPE
            SYNTAX Integer32
            MAX-ACCESS read-only
            STATUS current
            DESCRIPTION
                "
                Sub ID of extending frame.
                If extend type is ETH, sub ID is 0xffffffff, it is invalid.
                If extend type is GPON, sub ID is ont ID, it is valid.
                "
            ::= { hwFrameEntry 16 }


        -- 1.3.6.1.4.1.2011.6.3.3.1.1.17
        hwFrameExtendType OBJECT-TYPE
            SYNTAX Integer32
            MAX-ACCESS read-only
            STATUS current
            DESCRIPTION
                "
                The type of extended frame connecting to the main frame, its value is the same as the ifType of the extending port.
                "
            ::= { hwFrameEntry 17 }


        -- 1.3.6.1.4.1.2011.6.3.3.1.1.18
        hwFrameHardwareDesc OBJECT-TYPE
            SYNTAX OCTET STRING (SIZE (0..510))
            MAX-ACCESS read-only
            STATUS current
            DESCRIPTION
                "
                Hardware description of frame.
                "
            ::= { hwFrameEntry 18 }


        -- 1.3.6.1.4.1.2011.6.3.3.1.1.19
        hwFrameGponDeviceSn OBJECT-TYPE
            SYNTAX OCTET STRING (SIZE (0..8))
            MAX-ACCESS read-write
            STATUS current
            DESCRIPTION
                "
                ONT serial number. The valid length of the serial number is 8, and 0 indicates that the node is not set.
                "
            ::= { hwFrameEntry 19 }
            
            
        -- 1.3.6.1.4.1.2011.6.3.3.1.1.20
        hwFramePhySerialNum OBJECT-TYPE
            SYNTAX OCTET STRING (SIZE (0..32))
            MAX-ACCESS read-only
            STATUS current
            DESCRIPTION
                "
                The vendor-specific serial number string for the physical entity.
                The preferred value is the serial number string actually printed
                on the component itself.
                "
            ::= { hwFrameEntry 20 }

            
        -- 1.3.6.1.4.1.2011.6.3.3.1.1.65536
        hwFrameQueryAssit OBJECT-TYPE
            SYNTAX Integer32
            MAX-ACCESS read-only
            STATUS current
            DESCRIPTION
                "
                The number of assist frame of this frame.
                "
            ::= { hwFrameEntry 65536 }

        -- 1.3.6.1.4.1.2011.6.3.3.2
        hwSlotTable OBJECT-TYPE
            SYNTAX SEQUENCE OF HwSlotEntry
            MAX-ACCESS not-accessible
            STATUS current
            DESCRIPTION
                "
                The board description table, used to manage the running status of
                boards and board information, such as description of boards,
                daughter board quantity and board type.
                The indexes of this table are hwFrameIndex and hwSlotIndex.
                For the hwFrameIndex object, refer to hwFrameTable.
                For example, 0.2 indicates that the board is in slot 2, shelf 0.
                "
            ::= { hwSlotConf 2 }


        -- 1.3.6.1.4.1.2011.6.3.3.2.1
        hwSlotEntry OBJECT-TYPE
            SYNTAX HwSlotEntry
            MAX-ACCESS not-accessible
            STATUS current
            DESCRIPTION
                "
                The board description table, used to manage the running status of
                boards and board information, such as description of boards,
                daughter board quantity and board type.
                The indexes of this entry are hwFrameIndex and hwSlotIndex.
                For the hwFrameIndex object, refer to hwFrameTable.
                For example, 0.2 indicates that the board is in slot 2, shelf 0.
                "
            INDEX { hwFrameIndex, hwSlotIndex }
            ::= { hwSlotTable 1 }


        HwSlotEntry ::=
            SEQUENCE {
                hwSlotIndex
                    Integer32,
                hwSlotType
                    HWPCBType,
                hwSlotDesc
                    OCTET STRING,
                hwSlotPcbVersion
                    OCTET STRING,
                hwSlotVersion
                    OCTET STRING,
                hwSlotWorkMode
                    INTEGER,
                hwSubSlots
                    Integer32,
                hwSlotOperStatus
                    INTEGER,
                hwSlotAdminStatus
                    INTEGER,
                hwSlotRowStatus
                    RowStatus,
                hwSlotPhySerialNum
                    OCTET STRING,
                hwSlotShutdownState
                    INTEGER,
                hwSlotTemprature
                    Integer32,
                hwSlotUpdateVersion
                    OCTET STRING,
                hwSlotAdminForceOOSTime
                    Integer32,
                hwSlotForceOOSTime
                    Integer32,
                hwSlotAdminForceOOSTimeoutWorkMode
                    INTEGER,
                hwSlotEndServiceMode
                    INTEGER,
                hwSlotCLEICode
                    OCTET STRING,
                hwSlotNetworkRole
                    INTEGER,
                hwSlotTypeName
                    OCTET STRING,
                hwSlotPrimaryStatus
                    INTEGER,
                hwSlotSecondaryStatus
                    BITS,
                hwSlotCreateTime
                    DateAndTime
             }

        -- 1.3.6.1.4.1.2011.6.3.3.2.1.1
        hwSlotIndex OBJECT-TYPE
            SYNTAX Integer32 (0..255)
            MAX-ACCESS read-only
            STATUS current
            DESCRIPTION
                "
                A slot index is used to identify the location of a board in a shelf.
                You can locate a board in a shelf according to hwFrameIndex and hwSlotIndex.
                For the hwFrameIndex object, refer to hwFrameTable.
                "
            ::= { hwSlotEntry 1 }


        -- 1.3.6.1.4.1.2011.6.3.3.2.1.2
        hwSlotType OBJECT-TYPE
            SYNTAX HWPCBType
            MAX-ACCESS read-create
            STATUS current
            DESCRIPTION
                "
                Board type, which is defined in HUAWEI-TC-MIB.mib.
                The board type supported by a slot varies. For example, a slot can be inserted with a power board only,
                but certain slots can be inserted with voice service boards and broadband service boards.
                When adding a board by using the hwSlotRowStatus,
                you need to specify the board information such as board type and slot number.
                When adding a board, you need to check whether the board can be inserted in the specified slot.
                "
            ::= { hwSlotEntry 2 }


        -- 1.3.6.1.4.1.2011.6.3.3.2.1.3
        hwSlotDesc OBJECT-TYPE
            SYNTAX OCTET STRING (SIZE (0..64))
            MAX-ACCESS read-create
            STATUS current
            DESCRIPTION
                "
                The description about the board, providing additional information about a board for users.
                For example, you can set the services supported by the board as the description.
                "
            ::= { hwSlotEntry 3 }


        -- 1.3.6.1.4.1.2011.6.3.3.2.1.4
        hwSlotPcbVersion OBJECT-TYPE
            SYNTAX OCTET STRING (SIZE (0..64))
            MAX-ACCESS read-only
            STATUS deprecated
            DESCRIPTION
                "
                The PCB version information of the board.
                It has been discarded.
                The information of PCB version and other versions are described in the hwSlotVersion.
                "
            ::= { hwSlotEntry 4 }


        -- 1.3.6.1.4.1.2011.6.3.3.2.1.5
        hwSlotVersion OBJECT-TYPE
            SYNTAX OCTET STRING (SIZE (0..640))
            MAX-ACCESS read-only
            STATUS current
            DESCRIPTION
                "
                The version information about the board.
                Refer to the technical specifications of Huawei Technologies
                Co., Ltd. Use the new-line character \n (ACSII 0x0A) to space
                various version information. If there is no corresponding
                version, the new-line character shall also be inserted to
                remain the order.
                Detailed order information:
                Hardware PCB version \n
                Software version \n
                Logic version \n
                DSP version \n
                Standby CPU software version \n
                Chip version \n
                Other software version of the chip with a software \n
                Other version information \n
                The version information may have a slight difference according to different types of boards.
                For example, the standby CPU software version is not displayed for certain boards.
                "
            ::= { hwSlotEntry 5 }


        -- 1.3.6.1.4.1.2011.6.3.3.2.1.6
        hwSlotWorkMode OBJECT-TYPE
            SYNTAX INTEGER
                {
                main(1),
                standby(2),
                loadshare(3),
                nullbackup(4),
                voice(5),
                satop(6),
                pots(7),
                isdn(8),
                bonding(9),
                retransmission(10),
                nativetdm(11),
                other(255)
                }
            MAX-ACCESS read-write
            STATUS current
            DESCRIPTION
                "
                Board working mode that describes whether the board is
                working in main state or in standby with loadshare, nullbackup, voice, satop state.
                Options:
                1. main(1)                 - indicates that the active control board, supporting the get operation only
                2. standby(2)              - indicates that the standby control board, supporting the get operation only
                3. loadshare(3)            - indicates that the board working mode is load sharing
                4. nullbackup(4)           - indicates that the board working mode is backup
                5. voice(5)                - indicates to get and set the working mode of an EDT service board
                6. satop(6)                - indicates to get and set the working mode of an EDT service board or TOPB service board
                7. pots(7)                 - indicates to get and set the working mode of an VDM service board
                8. isdn(8)                 - indicates to get and set the working mode of an VDM service board
                9. bonding(9)              - indicates to get and set the working mode of an ADP service board
                10. retransmission(10)      - indicates to get and set the working mode of an ADP service board
                11. nativetdm(11)          - indicates to get and set the working mode of a TOPB service board
                12. other(255)             - indicates other working mode
                An EDT service board can be running either in voice mode, that is, voice(5), or in broadband mode, that is, satop(6).
                Setting the working mode of the EDT service board causes board resetting.
                An VDM service board can be running either in pots mode, that is, pots(7), or in isdn mode, that is, isdn(8).
                Setting the working mode of the VDM service board causes board resetting.
                Setting the board working mode may cause board resetting.
                When you are setting the working mode, you cannot set hwSlotAdminStatus or hwSlotRowStatus at the same time.
                "
            ::= { hwSlotEntry 6 }


        -- 1.3.6.1.4.1.2011.6.3.3.2.1.7
        hwSubSlots OBJECT-TYPE
            SYNTAX Integer32
            MAX-ACCESS read-only
            STATUS current
            DESCRIPTION
                "
                The number of sub boards supported by the board.
                "
            ::= { hwSlotEntry 7 }


        -- 1.3.6.1.4.1.2011.6.3.3.2.1.8
        hwSlotOperStatus OBJECT-TYPE
            SYNTAX INTEGER
                {
                null(1),
                normal(2),
                fault(3),
                forbidden(4),
                autofind(5),
                config(6),
                offline(7),
                abnormal(8),
                versionerr(9),
                autoload(10),
                outofservice(11),
                graceful(12),
                shutdown(13),
                energysavingshutdown(14),
                hightempshutdown(15),
                manualshutdown(16),
                mismatch(17),
                acoffshutdown(18)
                }
            MAX-ACCESS read-only
            STATUS current
            DESCRIPTION
                "
                The running status of a board.
                Options:
                1. null(1)                  -indicates that the board is null
                2. normal(2)                -indicates that the board is running normally
                3. fault(3)                 -indicates that the board is faulty but in position
                4. forbidden(4)             -indicates that the board is in position but disabled
                5. autofind(5)              -indicates that the board is in the autofind state. If a board is added through
                                             hwSlotRowStatus and the board is not confirmed, the board is in the autofind state.
                                             If a board is inserted in an idle slot, after the report of automatic registration,
                                             the board is also in the autofind state
                6. config(6)                -indicates that the board is in the configuration state.
                                             After a board that is in the auto discovery.
                                             state is confirmed, data needs to be configured on the board.
                                             The board is in the configuration state during data configuration.
                                             After a board is successfully configured, its status is changed from config(6)
                                             to normal(2). If the configuration fails, the board status is changed from config(6) to fault(3)
                7. offline(7)               -indicates that the board is faulty and is not in position
                8. abnormal(8)              -indicates that the board is abnormal
                9. versionerr(9)            -indicates that the board version is error

                10. autoload(10)            -indicates that the board is in the auto loading state. If detecting a software update,
                                             the board automatically loads the update. If a board is in the auto loading state,
                                             resetting or disabling the board may fail
                11. outofservice(11)        -indicates that the board is out of service
                12. graceful(12)            -indicates that the board running state is graceful
                13. shutdown(13)            -indicates that the board is in the shutdown state.
                14. energysavingshutdown(14)   -used for system energy saving. Reference to hwSysEnergySaving node for more detail.
                15. hightempshutdown(15)    -when the temperature of a board exceeds the high temperature threshold,
                                             the board is powered off in order to protect the board
                16. manualshutdown(16)       -services on certain boards can be recovered only after restart of the board.
                                             You can manually power off the board.
                                             Then, the board is in the manual shutdown state
                17. mismatch(17)            -when a board inserted in a slot is inconsistent with the configuration saved in the system,
                                             the board is in the mismatch(17) state
                18. acoffshutdown(18)       -used to protect system when there is no AC Power.
                Certain products use the power saving features, energysavingshutdown(14), hightempshutdown(15),
                manualshutdown(16),acoffshutdown(18) to distinguish the shutdown causes.
                For outofservice(11), graceful(12), refer to hwSlotEndServiceMode.
                "
            ::= { hwSlotEntry 8 }


        -- 1.3.6.1.4.1.2011.6.3.3.2.1.9
        hwSlotAdminStatus OBJECT-TYPE
            SYNTAX INTEGER
                {
                nooperation(-1),
                disable(1),
                enable(2),
                reset(3),
                test(4),
                confirm(5),
                switch(6),
                delete(7),
                forbidden(8),
                unforbidden(9),
                endservice(10),
                startservice(11),
                poweron(12),
                poweroff(13),
                is(14),
                oos(15),
                hotreset(16)
                }
            MAX-ACCESS read-create
            STATUS current
            DESCRIPTION
                "
                Board status management.
                This object cannot be set simultaneously with hwSlotRowStatus or hwSlotWorkMode.
                Options:
                1. nooperation(-1)   -default state of the system
                2. disable(1)        -disable the running of a board
                3. enable(2)         -enable the running of a board
                4. reset(3)          -reset a board
                5. test(4)           -test a board
                6. confirm(5)        -confirm the board in the discovery(5) state in hwSlotOperStatus
                                      After the operation, the board is in the config state
                7. switch(6)         -main board switchover on access network UA device
                8. delete(7)         -delete a board
                9. forbidden(8)      -forbid a board
                10.unforbidden(9)    -permit a board
                11.endservice(10)    -used in the exit delay of a board
                12.startservice(11)  -used in the exit delay of a board
                13.poweron(12)       -used to power on a board
                14.poweroff(13)      -used to power off a board
                15.is(14)            -in service
                16.oos(15)           -out of service
                17.hotreset(16)      -hotreset a board
                "
            ::= { hwSlotEntry 9 }


        -- 1.3.6.1.4.1.2011.6.3.3.2.1.10
        hwSlotRowStatus OBJECT-TYPE
            SYNTAX RowStatus
            MAX-ACCESS read-create
            STATUS current
            DESCRIPTION
                "
                Supported setting operations are createAndGo(4) and destroy(6).
                Options:
                1. CreateAndGo(4) - When adding a board in offline mode, you must set the hwSlotType object at
                                    the same time. The hwSlotType object must support offline adding.
                                    After you add a board in offline mode on the NMS, if adding a daughter board is supported,
                                    you can also add a daughter board. See hwSubslotAdminStatus in hwSubslotTable.
                2. Destroy(6)     - Used to delete a board.
                "
            ::= { hwSlotEntry 10 }


        -- 1.3.6.1.4.1.2011.6.3.3.2.1.11
        hwSlotPhySerialNum OBJECT-TYPE
            SYNTAX OCTET STRING (SIZE (0..32))
            MAX-ACCESS read-only
            STATUS current
            DESCRIPTION
                "
                The vendor-specific serial number string for the board.
                The preferred value is the serial number string actually printed on the component itself.
                "
            ::= { hwSlotEntry 11 }


        -- 1.3.6.1.4.1.2011.6.3.3.2.1.12
        hwSlotShutdownState OBJECT-TYPE
            SYNTAX INTEGER
                {
                powerOffState(1),
                powerOnState(2)
                }
            MAX-ACCESS read-only
            STATUS current
            DESCRIPTION
                "
                Shutdown state of the board.
                Options:
                1. powerOffState(1)  -indicates the power-off state
                2. powerOnState(2)   -indicates the power-on state
                This object is no longer used.
                "
            ::= { hwSlotEntry 12 }


        -- 1.3.6.1.4.1.2011.6.3.3.2.1.13
        hwSlotTemprature OBJECT-TYPE
            SYNTAX Integer32
            UNITS "centigrade"
            MAX-ACCESS read-only
            STATUS current
            DESCRIPTION
                "
                The temperature of the board. (Unit:centigrade)
                The value 0X7FFFFFFF indicates invalid temperature.
                "
            ::= { hwSlotEntry 13 }


        -- 1.3.6.1.4.1.2011.6.3.3.2.1.14
        hwSlotUpdateVersion OBJECT-TYPE
            SYNTAX OCTET STRING (SIZE (0..32))
            MAX-ACCESS read-only
            STATUS current
            DESCRIPTION
                "
                The message is reported if the current version of a board is inconsistent with the
                version saved in the flash memory.
                The contents of the message are as follows:
                Current BIOS version of the board      3 bytes
                BIOS version of the board in the flash   3 bytes
                Current software version of the board      3 bytes
                Software version of the board in the flash memory   3 bytes
                "
            ::= { hwSlotEntry 14 }


        -- 1.3.6.1.4.1.2011.6.3.3.2.1.15
        hwSlotAdminForceOOSTime OBJECT-TYPE
            SYNTAX Integer32 (1..1440)
            UNITS "minutes"
            MAX-ACCESS read-create
            STATUS current
            DESCRIPTION
                "
                The timeout time before forcing to quit service of the board, in unit of minutes.
                Range: 1-1440
                Default: 0
                Unit: minutes
                "
            DEFVAL { 0 }
            ::= { hwSlotEntry 15 }


        -- 1.3.6.1.4.1.2011.6.3.3.2.1.16
        hwSlotForceOOSTime OBJECT-TYPE
            SYNTAX Integer32 (0..86400)
            MAX-ACCESS read-only
            STATUS current
            DESCRIPTION
                "
                The remain time of the forcing to out of service.
                Unit:Minute
                "
            ::= { hwSlotEntry 16 }


        -- 1.3.6.1.4.1.2011.6.3.3.2.1.17
        hwSlotAdminForceOOSTimeoutWorkMode OBJECT-TYPE
            SYNTAX INTEGER
                {
                forced(1),
                cancel(2)
                }
            MAX-ACCESS read-create
            STATUS current
            DESCRIPTION
                "
                The handling after the timeout time elapses when a board delays in quitting service.
                Options:
                        1. forced(1)   - force to handle    
                        2. cancel(2)   - cancel handling 
                        "
                 DEFVAL {cancel}
                 ::= { hwSlotEntry  17 }
            
        -- 1.3.6.1.4.1.2011.6.3.3.2.1.18
        hwSlotEndServiceMode OBJECT-TYPE
            SYNTAX INTEGER
                {
                immediate(1),
                graceful(2)
                }
            MAX-ACCESS read-create
            STATUS current
            DESCRIPTION
                "
                The mode in which a board quits service.
                Options:
                1. immediate(1) -quit service immediately
                2. graceful(2)  -quit service later
                "
            ::= { hwSlotEntry 18 }


        -- 1.3.6.1.4.1.2011.6.3.3.2.1.19
        hwSlotCLEICode OBJECT-TYPE
            SYNTAX OCTET STRING (SIZE (0..640))
            MAX-ACCESS read-only
            STATUS current
            DESCRIPTION
                "
                Card CLEI Code(COMMON LANGUAGE Location Identifier Code):
                Used to identify the location and the type of a telecommunication device.
                For the definition of the CLEI Code, refer to the GR-485.
                "
            ::= { hwSlotEntry 19 }


        -- 1.3.6.1.4.1.2011.6.3.3.2.1.20
        hwSlotNetworkRole OBJECT-TYPE
            SYNTAX INTEGER
                {
                cascade(1),
                network(2),
                user(3),
                extend(4),
                invalid(255)
                }
            MAX-ACCESS read-write
            STATUS current
            DESCRIPTION
                "
                Indicates the network role of a board.
                Options:
                1. cascade(1)  -indicates the subtending side, which is used for subtending and capturing certain protocol packets
                2. network(2)  -indicates the network side, which is used for upstream transmission
                3. user(3)     -indicates the user side, which is used for creating the service port
                4. extend(4)   -indicates the extend side, which is used for connecting to the extended frame
                5. invalid(255)-indicates the invalid value
                "
            ::= { hwSlotEntry 20 }


        -- 1.3.6.1.4.1.2011.6.3.3.2.1.21
        hwSlotTypeName OBJECT-TYPE
            SYNTAX OCTET STRING (SIZE (0..64))
            MAX-ACCESS read-only
            STATUS current
            DESCRIPTION
                "
                Slot information description, to describe board name information of the slot.
                "
            ::= { hwSlotEntry 21 }


        -- 1.3.6.1.4.1.2011.6.3.3.2.1.22
        hwSlotPrimaryStatus OBJECT-TYPE
            SYNTAX INTEGER
                {
                isNr(1),
                isAnr(2),
                isRst(3),
                isAnrst(4),
                oosAu(5),
                oosMa(6),
                oosAuma(7),
                oosAurst(8),
                oosMaanr(9),
                unknown(10)                
                }
            MAX-ACCESS read-only
            STATUS current
            DESCRIPTION
                "
                The primary status of the Board.
                Options:
                1. isNr(1)     -in Service, normal
                2. isAnr(2)    -in service, abnormal
                3. isRst(3)    -in service, restricted
                4. isAnrst(4)  -in service, abnormal & restricted
                5. oosAu(5)    -out of service, autonomous
                6. oosMa(6)    -out of service, management
                7. oosAuma(7)  -out of service, autonomous & management
                8. oosAurst(8) -out of service, autonomous & restricted
                9. oosMaanr(9) -out of service, management & abnormal
                10. unknown(10) -unknown                
                "
            ::= { hwSlotEntry 22 }


        -- 1.3.6.1.4.1.2011.6.3.3.2.1.23
        hwSlotSecondaryStatus OBJECT-TYPE
            SYNTAX BITS
                {
                sstAins(0),
                sstFaf(1),
                sstFlt(2),
                sstLpbk(3),
                sstMea(4),
                sstSgeo(5),
                sstStbyh(6),
                sstTs(7),
                sstUas(8),
                sstUeq(9),
                sstWrk(10),
                sstPwr(11)
                }
            MAX-ACCESS read-only
            STATUS current
            DESCRIPTION
                "
                The secondary status of the board.
                This BITS structure can report the following status:
                1. sstAins(0)  -this bit position positively reports that the status of the board is automatic in-service
                2. sstFaf(1)   -facility failure
                3. sstFlt(2)   -fault
                4. sstLpbk(3)  -loopback
                5. sstMea(4)   -mismatch of equipment and attributes
                6. sstSgeo(5)  -supporting entity outage
                7. sstStbyh(6) -standby-Hot
                8. sstTs(7)    -test
                9. sstUas(8)   -unassigned
                10. sstUeq(9)  -unequipped
                11. sstWrk(10) -working
                12. sstPwr(11) -power
                "
            ::= { hwSlotEntry 23 }


        -- 1.3.6.1.4.1.2011.6.3.3.2.1.24
        hwSlotCreateTime OBJECT-TYPE
            SYNTAX DateAndTime
            MAX-ACCESS read-only
            STATUS current
            DESCRIPTION
                "
                This object is used for getting the time of adding or creating a board.
                "
            ::= { hwSlotEntry 24 }


        -- 1.3.6.1.4.1.2011.6.3.3.3
        hwSubslotTable OBJECT-TYPE
            SYNTAX SEQUENCE OF HwSubslotEntry
            MAX-ACCESS not-accessible
            STATUS current
            DESCRIPTION
                "
                Subslot description table that describes detailed information of each subslot attached to the board.
                The indexes of this table are hwFrameIndex, hwSlotIndex and hwSubslotIndex.
                For the hwFrameIndex object, refer to hwFrameTable; for the hwSlotIndex object, refer to hwSlotTable.
                For example, 0.1.0 indicates that a daughter board is in subslot 0, slot 1, shelf 0.
                "
            ::= { hwSlotConf 3 }


        -- 1.3.6.1.4.1.2011.6.3.3.3.1
        hwSubslotEntry OBJECT-TYPE
            SYNTAX HwSubslotEntry
            MAX-ACCESS not-accessible
            STATUS current
            DESCRIPTION
                "
                Subslot description table that describes detailed information of each subslot attached to the board.
                The indexes of this entry are hwFrameIndex, hwSlotIndex and hwSubslotIndex.
                For the hwFrameIndex object, refer to hwFrameTable; for the hwSlotIndex object, refer to hwSlotTable.
                For example, 0.1.0 indicates that a daughter board is in subslot 0, slot 1, shelf 0.
                "
            INDEX { hwFrameIndex, hwSlotIndex, hwSubslotIndex }
            ::= { hwSubslotTable 1 }


        HwSubslotEntry ::=
            SEQUENCE {
                hwSubslotIndex
                    Integer32,
                hwSubslotType
                    HWSubPCBType,
                hwSubslotPorts
                    Integer32,
                hwSubslotOperStatus
                    INTEGER,
                hwSubslotAdminStatus
                    INTEGER,
                hwSubslotVersion
                    OCTET STRING,
                hwSubSlotDesc
                    OCTET STRING,
                hwSubslotRowStatus
                    RowStatus,
                hwSubSlotPhySerialNum
                    OCTET STRING,
                hwSubslotTypeName
                    OCTET STRING,
                hwSubslotPrimaryStatus
                    INTEGER,
                hwSubslotSecondaryStatus
                    BITS,
                hwSubslotCLEICode
                    OCTET STRING,
                hwSubslotTemperature
                    Integer32,
                hwSubslotCpuRate
                    Integer32,
                hwSubslotRamUseRate
                    Integer32
             }

        -- 1.3.6.1.4.1.2011.6.3.3.3.1.1
        hwSubslotIndex OBJECT-TYPE
            SYNTAX Integer32 (0..255)
            MAX-ACCESS read-only
            STATUS current
            DESCRIPTION
                "
                The index of a daughter board is determined by the physical position of the daughter board on the board.
                The hwSubslotIndex value of 65535 indicates the board itself.
                "
            ::= { hwSubslotEntry 1 }


        -- 1.3.6.1.4.1.2011.6.3.3.3.1.2
        hwSubslotType OBJECT-TYPE
            SYNTAX HWSubPCBType
            MAX-ACCESS read-create
            STATUS current
            DESCRIPTION
                "
                For the definition of the daughter board type, refer to the HUAWEI-TC-MIB.mib.
                When adding a daughter board on a board, you need to specify the type of the daughter board and
                check whether the daughter board can be inserted in the specified subslot on the board.
                "
            ::= { hwSubslotEntry 2 }


        -- 1.3.6.1.4.1.2011.6.3.3.3.1.3
        hwSubslotPorts OBJECT-TYPE
            SYNTAX Integer32
            MAX-ACCESS read-only
            STATUS current
            DESCRIPTION
                "
                The number of physical ports owned by the sub board.
                "
            ::= { hwSubslotEntry 3 }


        -- 1.3.6.1.4.1.2011.6.3.3.3.1.5
        hwSubslotOperStatus OBJECT-TYPE
            SYNTAX INTEGER
                {
                uninstall(1),
                normal(2),
                fault(3),
                forbidden(4),
                autofind(5),
                config(6),
                offline(7),
                abnormal(8),
                versionerr(9),
                autoload(10),
                outofservice(11),
                graceful(12),
                shutdown(13),
                energysavingshutdown(14),
                hightempshutdown(15),
                manualshutdown(16),
                mismatch(17),
                acoffshutdown(18)
                }
            MAX-ACCESS read-only
            STATUS current
            DESCRIPTION
                "
                Operation status of the daughter board.
                Options:
                1. uninstall(1)             -indicates that the daughter board is not installed
                2. normal(2)                -indicates that the daughter board is running normally
                3. fault(3)                 -indicates that the daughter board is faulty
                4. forbidden(4)             -the object is not used
                5. autofind(5)              -indicates that the daughter board is in the autofind state.
                6. config(6)                -indicates that the daughter board is in the configuration state.
                                             The daughter board is in the configuration state during data configuration.
                                             After a daughter board is successfully configured, its status is changed from config(6)
                                             to normal(2). If the configuration fails, the daughter board status is changed from config(6) to fault(3)
                7. offline(7)               -indicates that the daughter board is faulty and is not in position
                8. abnormal(8)              -indicates that the daughter board is abnormal
                9. versionerr(9)            -indicates that the daughter board version is error
                10. autoload(10)            -indicates that the daughter board is in the auto loading state. If detecting a software update,
                                             the daughter board automatically loads the update. If a daughter board is in the auto loading state,
                                             resetting or disabling the daughter board may fail
                11. outofservice(11)        -indicates that the daughter board is out of service
                12. graceful(12)            -indicates that the daughter board running state is graceful
                13. shutdown(13)            -indicates that the daughter board is in the shutdown state.
                14. energysavingshutdown(14)   -used for system energy saving. Reference to hwSysEnergySaving node for more detail.
                15. hightempshutdown(15)    -when the temperature of a daughter board exceeds the high temperature threshold,
                                             the daughter board is powered off in order to protect the daughter board
                16. manualshutdown(16)       -services on certain daughter boards can be recovered only after restart of the daughter board.
                                             You can manually power off the daughter board.
                                             Then, the daughter board is in the manual shutdown state
                17. mismatch(17)            -when a daughter board inserted in a slot is inconsistent with the configuration saved in the system,
                                             the daughter board is in the mismatch(17) state
                18. acoffshutdown(18)       -used to protect system when there is no AC Power.
                Certain products use the power saving features, energysavingshutdown(14), hightempshutdown(15),
                manualshutdown(16),acoffshutdown(18) to distinguish the shutdown causes.
                "
            ::= { hwSubslotEntry 5 }


        -- 1.3.6.1.4.1.2011.6.3.3.3.1.7
        hwSubslotAdminStatus OBJECT-TYPE
            SYNTAX INTEGER
                {
                nooperation(-1),
                disable(1),
                enable(2),
                reset(3),
                test(4),
                confirm(5),
                delete(6),
                is(7),
                oos(8),
                poweron(9),
                poweroff(10)
                }
            MAX-ACCESS read-create
            STATUS current
            DESCRIPTION
                "
                Administration status of the daughter board in the subslot.
                This object is not used.
                Options:
                1. nooperation(-1)  -indicates the default state
                2. disable(1)       -indicates the disable state
                3. enable(2)        -indicates the enable state
                4. reset(3)         -indicates the reset state
                5. test(4)          -indicates the test state
                6. confirm(5)       -indicates the confirmation state
                7. delete(6)        -indicates the delete state
                8. is(7)            -indicates in service
                9. oos(8)           -indicates out of service
                10. poweron(9)      -indicates the poweron state
                11. poweroff(10)    -indicates the poweroff state
                "
            ::= { hwSubslotEntry 7 }


        -- 1.3.6.1.4.1.2011.6.3.3.3.1.8
        hwSubslotVersion OBJECT-TYPE
            SYNTAX OCTET STRING (SIZE (0..1024))
            MAX-ACCESS read-create
            STATUS current
            DESCRIPTION
                "
                daughter board version information, obtained from the version information about the
                board on which the daughter board is located.
                Refer to the hwSlotVersion in the hwSlotTable.
                "
            ::= { hwSubslotEntry 8 }


        -- 1.3.6.1.4.1.2011.6.3.3.3.1.9
        hwSubSlotDesc OBJECT-TYPE
            SYNTAX OCTET STRING (SIZE (0..64))
            MAX-ACCESS read-create
            STATUS current
            DESCRIPTION
                "
                The description about the daughter board.
                Do not support the setting operation.
                "
            ::= { hwSubslotEntry 9 }


        -- 1.3.6.1.4.1.2011.6.3.3.3.1.10
        hwSubslotRowStatus OBJECT-TYPE
            SYNTAX RowStatus
            MAX-ACCESS read-create
            STATUS current
            DESCRIPTION
                "
                Only the operation of adding a daughter board, that is, setting createAndGo(4),
                is supported. When adding a daughter board, you must set the hwSubslotType object at the same time.
                After you add a board by using the hwSlotAdminStatus object in hwSlotTable,
                if the board allows you to add a daughter board and the board status (hwSlotOperStatus) is discovery(5),
                you can add a daughter board in this way.
                "
            ::= { hwSubslotEntry 10 }


        -- 1.3.6.1.4.1.2011.6.3.3.3.1.11
        hwSubSlotPhySerialNum OBJECT-TYPE
            SYNTAX OCTET STRING (SIZE (0..32))
            MAX-ACCESS read-only
            STATUS current
            DESCRIPTION
                "
                The vendor-specific serial number string for the daughter board.
                The preferred value is the serial number string
                actually printed on the component itself.
                "
            ::= { hwSubslotEntry 11 }


        -- 1.3.6.1.4.1.2011.6.3.3.3.1.12
        hwSubslotTypeName OBJECT-TYPE
            SYNTAX OCTET STRING (SIZE (0..64))
            MAX-ACCESS read-only
            STATUS current
            DESCRIPTION
                "
                daughter board type name in the subslot,refer to the HW-TC table.
                "
            ::= { hwSubslotEntry 12 }


        -- 1.3.6.1.4.1.2011.6.3.3.3.1.13
        hwSubslotPrimaryStatus OBJECT-TYPE
            SYNTAX INTEGER
                {
                isNr(1),
                isAnr(2),
                isRst(3),
                isAnrst(4),
                oosAu(5),
                oosMa(6),
                oosAuma(7),
                oosAurst(8),
                oosMaanr(9)
                }
            MAX-ACCESS read-only
            STATUS current
            DESCRIPTION
                "
                The primary status of the daughter board.
                Options:
                1. isNr(1)     -in Service, normal
                2. isAnr(2)    -in service, abnormal
                3. isRst(3)    -in service, restricted
                4. isAnrst(4)  -in service, abnormal & restricted
                5. oosAu(5)    -out of service, autonomous
                6. oosMa(6)    -out of service, management
                7. oosAuma(7)  -out of service, autonomous & management
                8. oosAurst(8) -out of service, autonomous & restricted
                9. oosMaanr(9) -out of service, management & abnormal
                "
            ::= { hwSubslotEntry 13 }


        -- 1.3.6.1.4.1.2011.6.3.3.3.1.14
        hwSubslotSecondaryStatus OBJECT-TYPE
            SYNTAX BITS
                {
                sstAins(0),
                sstFaf(1),
                sstFlt(2),
                sstLpbk(3),
                sstMea(4),
                sstSgeo(5),
                sstStbyh(6),
                sstTs(7),
                sstUas(8),
                sstUeq(9),
                sstWrk(10),
                sstPwr(11)
                }
            MAX-ACCESS read-only
            STATUS current
            DESCRIPTION
                "
                The secondary status of the daughter board.
                This BITS structure can report the following status:
                1. sstAins(0)  -this bit position positively reports that the status of the daughter board is automatic in-service
                2. sstFaf(1)   -facility failure
                3. sstFlt(2)   -fault
                4. sstLpbk(3)  -loopback
                5. sstMea(4)   -mismatch of equipment and attributes
                6. sstSgeo(5)  -supporting entity outage
                7. sstStbyh(6) -standby-Hot
                8. sstTs(7)    -test
                9. sstUas(8)   -unassigned
                10. sstUeq(9)  -unequipped
                11. sstWrk(10) -working
                12. sstPwr(11) -power
                "
            ::= { hwSubslotEntry 14 }


        -- 1.3.6.1.4.1.2011.6.3.3.3.1.15
        hwSubslotCLEICode OBJECT-TYPE
            SYNTAX OCTET STRING (SIZE (0..640))
            MAX-ACCESS read-only
            STATUS current
            DESCRIPTION
                "
                daughter board CLEI Code(COMMON LANGUAGE Location Identifier Code):
                Used to identify the location and the type of a telecommunication device.
                For the definition of the CLEI Code, refer to the GR-485.
                        "
            ::= { hwSubslotEntry 15 }


        -- 1.3.6.1.4.1.2011.6.3.3.3.1.16
        hwSubslotTemperature OBJECT-TYPE
            SYNTAX Integer32
            UNITS "centigrade"
            MAX-ACCESS read-only
            STATUS current
            DESCRIPTION
                "
                The temperature of the daughter board. (Unit:centigrade)
                The value 0X7FFFFFFF indicates invalid temperature.
                "
            ::= { hwSubslotEntry 16 }


        -- 1.3.6.1.4.1.2011.6.3.3.3.1.17
        hwSubslotCpuRate OBJECT-TYPE
            SYNTAX Integer32 (-1 | 0..100)
            MAX-ACCESS read-only
            STATUS current
            DESCRIPTION
                "
                The cpu occupancy of the daughter board.
                The value -1 indicates invalid cpu occupancy.
                "
            ::= { hwSubslotEntry 17 }


        -- 1.3.6.1.4.1.2011.6.3.3.3.1.18
        hwSubslotRamUseRate OBJECT-TYPE
            SYNTAX Integer32 (-1 | 0..100)
            MAX-ACCESS read-only
            STATUS current
            DESCRIPTION
                "
                The memory occupancy of the daughter board.
                The value -1 indicates invalid memory occupancy.
                "
            ::= { hwSubslotEntry 18 }


        -- 1.3.6.1.4.1.2011.6.3.3.4
        hwPortTable OBJECT-TYPE
            SYNTAX SEQUENCE OF HwPortEntry
            MAX-ACCESS not-accessible
            STATUS current
            DESCRIPTION
                "Port configuration table that describes the detailed
                information of physical ports in the board, including the type,
                status and rate of the port. This table must be implemented.
                The indexes of this table are hwFrameIndex, hwSlotIndex, hwSubslotIndex and hwPortIndex.
                hwFrameIndex refer to hwFrameTable, hwSlotIndex refer to
                hwSlotTable, hwSubslotIndex refer to hwSubslotTable.
                "
            ::= { hwSlotConf 4 }


        -- 1.3.6.1.4.1.2011.6.3.3.4.1
        hwPortEntry OBJECT-TYPE
            SYNTAX HwPortEntry
            MAX-ACCESS not-accessible
            STATUS current
            DESCRIPTION
                "Port configuration table that describes the detailed
                information of physical ports in the board, including the type,
                status and rate of the port. This table must be implemented.
                The indexes of this entry are hwFrameIndex, hwSlotIndex, hwSubslotIndex and hwPortIndex.
                hwFrameIndex refer to hwFrameTable, hwSlotIndex refer to hwSlotTable,
                hwSubslotIndex refer to hwSubslotTable.
                "
            INDEX { hwFrameIndex, hwSlotIndex, hwSubslotIndex, hwPortIndex }
            ::= { hwPortTable 1 }


        HwPortEntry ::=
            SEQUENCE {
                hwPortIndex
                    Integer32,
                hwPortType
                    HWPortType,
                hwPortDesc
                    OCTET STRING,
                hwPortSpeed
                    Integer32,
                hwPortOperStatus
                    INTEGER,
                hwPortAdminStatus
                    INTEGER,
                hwPortNetworkRole
                    INTEGER,
                hwPortTemprature
                    Integer32,
                hwPortPrimaryStatus
                    INTEGER,
                hwPortSecondaryStatus
                    BITS,
                hwPortVsIDMask
                    Integer32    
             }

        -- 1.3.6.1.4.1.2011.6.3.3.4.1.1
        hwPortIndex OBJECT-TYPE
            SYNTAX Integer32 (0..255)
            MAX-ACCESS read-only
            STATUS current
            DESCRIPTION
                "
                Port index, indicating the physical number of the port on a board.
                "
            ::= { hwPortEntry 1 }


        -- 1.3.6.1.4.1.2011.6.3.3.4.1.2
        hwPortType OBJECT-TYPE
            SYNTAX HWPortType
            MAX-ACCESS read-only
            STATUS current
            DESCRIPTION
                "
                Port type, which is defined in HUAWEI-TC-MIB.mib.
                "
            ::= { hwPortEntry 2 }


        -- 1.3.6.1.4.1.2011.6.3.3.4.1.3
        hwPortDesc OBJECT-TYPE
            SYNTAX OCTET STRING (SIZE (0..80))
            MAX-ACCESS read-write
            STATUS current
            DESCRIPTION
                "
                The description about the port, used to describe extra information of the port.
                For example, you can describe the user that connects to the port.
                The standby control board does not support setting of the port description.
                "
            ::= { hwPortEntry 3 }


        -- 1.3.6.1.4.1.2011.6.3.3.4.1.4
        hwPortSpeed OBJECT-TYPE
            SYNTAX Integer32
            MAX-ACCESS read-only
            STATUS deprecated
            DESCRIPTION
                "
                The speed of the port.
                Unit:Kbps
                "
            ::= { hwPortEntry 4 }


        -- 1.3.6.1.4.1.2011.6.3.3.4.1.5
        hwPortOperStatus OBJECT-TYPE
            SYNTAX INTEGER
                {
                normal(1),
                fault(2),
                localLoopback(3),
                forbidden(4),
                test(5),
                remoteLoopback(6),
                activated(10),
                deactivated(11),
                block(12),
                nolight(13),
                innerLocalLoopback(14),
                innerRemoteLoopback(15),
                locked(16),
                busy(17),
                maintain(18),
                standbynormal(19),
                standbyfault(20),
                adslloopbackafe(21),
                adslloopbackhybrid(22),
                rtuLocalLoopback(23),
                rtuRemoteLoopback(24),
                linkup(25),
                linkdown(26),
                powerDenied(50)
                }
            MAX-ACCESS read-only
            STATUS current
            DESCRIPTION
                "
                Port operation status.
                Options:
                1.normal(1)               -indicates that the link is up or activated
                2.fault(2)                -indicates that port failure
                3.localLoopback(3)        -indicates that normal local loopback
                4.forbidden(4)            -indicates that the port is disabled
                5.test(5)                 -indicates test start
                6.remoteLoopback(6)       -indicates normal remote loopback
                7.activated(10)          -indicates that the port is being activated
                8.deactivated(11)         -indicates that the link is down or deactivated
                9.block(12)               -indicates port blocking
                10.nolight(13)            -indicates no signal in ATM port
                11.innerLocalLoopback(14) -indicates that inner local loopback toward inner system chipset (it's UTOPIA loopback for ADSL port)
                12.innerRemoteLoopback(15)-indicates that inner remote loopback toward inner system chipset
                13.locked(16)             -indicates locked
                14.busy(17)               -indicates busy
                15.maintain(18)           -indicates maintenance
                16.standbynormal(19)      -indicates that the port on the standby control board is activated
                17.standbyfault(20)       -indicates that the port on the standby control board is faulty
                18.adslloopbackafe(21)    -indicates that AFE loopback
                19.adslloopbackhybrid(22) -indicates that HYBRID loopback
                20.rtuLocalLoopback(23)   -indicates that RTU local loopback
                21.rtuRemoteLoopback(24)  -indicates that RTU remote loopback
                22.linkup(25)             -indicates eth port online
                23.linkdown(26)           -indicates eth port offline
                24.powerDenied(50)        -indicates port operation state is power denied
                "
            ::= { hwPortEntry 5 }


        -- 1.3.6.1.4.1.2011.6.3.3.4.1.6
        hwPortAdminStatus OBJECT-TYPE
            SYNTAX INTEGER
                {
                active(1),
                deactive(2),
                block(3),
                unblock(4),
                confirm(5),
                delete(6),
                reset(7),
                localLoopback(8),
                remoteLoopback(9),
                stopLoopback(11),
                innerLocalLoopback(12),
                innerRemoteLoopback(13),
                rtuLocalLoopback(14),
                rtuRemoteLoopback(15),
                utopiaLocalLoopback(16),
                afeLocalLoopback(17),
                hybirdLocalLoopback(18),
                noLoopBackNoTest(50),
                noLoopBackTest(51),
                localLoopBackNoTest(52),
                localLoopBackTest(53),
                remoteLoopBackNoTest(54),
                remoteLoopBackTest(55),
                localLoopbackPTM(56),
                eocLoopbackNoTest(57),
                eocLoopbackTest(58),
                prohibited(59)
                }
            MAX-ACCESS read-write
            STATUS current
            DESCRIPTION
                "
                Port administration status.
                Options:
                1.active(1)                   -activate the port
                2.deactive(2)                 -deactivate the port
                3.block(3)                    -block the port
                4.unblock(4)                  -unblock the port
                5.confirm(5)                  -confirm the port
                6.delete(6)                   -delete the port
                7.reset(7)                    -reset the port
                8.localLoopback(8)            -loop back the port
                9.remoteLoopback(9)           -remotely loop back the port
                10.stopLoopback(11)            -stop looping back the port
                11.innerLocalLoopback(12)      -inner local loopback toward inner system chipset
                12.innerRemoteLoopback(13)     -inner remote loopback toward inner system chipset
                13.rtuLocalLoopback(14)        -RTU local loopback RUT: Local loopback
                14.rtuRemoteLoopback(15)       -RTU remote loopback
                15.utopiaLocalLoopback(16)     -UTOPIA Local Loopback
                16.afeLocalLoopback(17)        -AFE Local Loopback
                17.hybirdLocalLoopback(18)     -HYBIRD Local Loopback
                18.noLoopBackNoTest(50)        -no loop back and no test
                19.noLoopBackTest(51)          -no loop back and test
                20.localLoopBackNoTest(52)     -Local loop back and no test
                21.localLoopBackTest(53)       -Local loop back test
                22.remoteLoopBackNoTest(54)    -Remote loopback and no test
                23.remoteLoopBackTest(55)      -Remote loopback and test
                24.localLoopbackPTM(56)        -PTM Local Loopback
                25.eocLoopbackNoTest(57)       -EOC Loop back and no test
                26.eocLoopbackTest(58)         -EOC Loop back and test
                27.prohibited(59)              -Port is prohibited
                "
            ::= { hwPortEntry 6 }


        -- 1.3.6.1.4.1.2011.6.3.3.4.1.7
        hwPortNetworkRole OBJECT-TYPE
            SYNTAX INTEGER
                {
                uplink(1),
                cascade(2),
                access(3),
                extend(4)
                }
            MAX-ACCESS read-write
            STATUS current
            DESCRIPTION
                "
                Indicates the network role of a board.
                Options:
                1. uplink(1)  -indicates the uplink port
                2. cascade(2) -indicates the subtending port
                3. access(3)  -indicates the downstream access port
                4. extend(4)  -indicates connectting to extended frame
                "
            ::= { hwPortEntry 7 }


        -- 1.3.6.1.4.1.2011.6.3.3.4.1.8
        hwPortTemprature OBJECT-TYPE
            SYNTAX Integer32
            MAX-ACCESS read-only
            STATUS current
            DESCRIPTION
                "
                The temperature of the port.
                The object is not used.
                "
            ::= { hwPortEntry 8 }


        -- 1.3.6.1.4.1.2011.6.3.3.4.1.9
        hwPortPrimaryStatus OBJECT-TYPE
            SYNTAX INTEGER
                {
                isNr(1),
                isAnr(2),
                isRst(3),
                isAnrst(4),
                oosAu(5),
                oosMa(6),
                oosAuma(7),
                oosAurst(8),
                oosMaanr(9)
                }
            MAX-ACCESS read-only
            STATUS current
            DESCRIPTION
                "
                The primary status of the port.
                Options:
                1. isNr(1)     -in Service, normal
                2. isAnr(2)    -in service, abnormal
                3. isRst(3)    -in service, restricted
                4. isAnrst(4)  -in service, abnormal & restricted
                5. oosAu(5)    -out of service, autonomous
                6. oosMa(6)    -out of service, management
                7. oosAuma(7)  -out of service, autonomous & management
                8. oosAurst(8) -out of service, autonomous & restricted
                9. oosMaanr(9) -out of service, management & abnormal
                "
            ::= { hwPortEntry 9 }


        -- 1.3.6.1.4.1.2011.6.3.3.4.1.10
        hwPortSecondaryStatus OBJECT-TYPE
            SYNTAX BITS
                {
                sstAins(0),
                sstFaf(1),
                sstFlt(2),
                sstLpbk(3),
                sstMea(4),
                sstSgeo(5),
                sstStbyh(6),
                sstTs(7),
                sstUas(8),
                sstUeq(9),
                sstWrk(10),
                sstPwr(11)
                }
            MAX-ACCESS read-only
            STATUS current
            DESCRIPTION
                "
                The secondary status of the port.
                This BITS structure can report the following status:
                1. sstAins(0)  -this bit position positively reports that the status of the port is automatic in-service
                2. sstFaf(1)   -facility failure
                3. sstFlt(2)   -fault
                4. sstLpbk(3)  -loopback
                5. sstMea(4)   -mismatch of equipment and attributes
                6. sstSgeo(5)  -supporting entity outage
                7. sstStbyh(6) -standby-Hot
                8. sstTs(7)    -test
                9. sstUas(8)   -unassigned
                10. sstUeq(9)  -unequipped
                11. sstWrk(10) -working
                12. sstPwr(11) -power
                "
            ::= { hwPortEntry 10 }

                      
        -- 1.3.6.1.4.1.2011.6.3.3.4.1.11
        hwPortVsIDMask OBJECT-TYPE
            SYNTAX Integer32
            MAX-ACCESS read-only
            STATUS current
            DESCRIPTION
                "
                The virtual system mask of the port, each bit indicates the VAN to which the board
                belongs. For example, the first bit maps vs0, the second bit maps vs1, and the rest 
                can be deducted by analog.
                 "
            ::= { hwPortEntry 11 }
                                
                                
        -- 1.3.6.1.4.1.2011.6.3.3.5
        hwFrameLinks OBJECT IDENTIFIER ::= { hwSlotConf 5 }


        -- 1.3.6.1.4.1.2011.6.3.3.5.1
        hwFrameLinkNumber OBJECT-TYPE
            SYNTAX Integer32
            MAX-ACCESS read-write
            STATUS current
            DESCRIPTION
                "
                Number of frame Links, which refers to the number of links between the main
                frame and the standby frame of the current device. If there are many frames,
                but the device cannot know the link relation of the frames, then the initial
                value of this node is 0. If a user manually adds the link between the frames later,
                then this node shall be renewed.
                Default: 0
                "
            ::= { hwFrameLinks 1 }


        -- 1.3.6.1.4.1.2011.6.3.3.5.2
        hwFrameLinkTable OBJECT-TYPE
            SYNTAX SEQUENCE OF HwFrameLinkEntry
            MAX-ACCESS not-accessible
            STATUS current
            DESCRIPTION
                "
                The index of this table is hwFrameLinkIndex.
                The frame link table. It describes the topology relation between the frames.
                For the device that can automatically discover the link relationship between the devices,
                this table can be implemented as read-only table. For the device whose inter-frame
                relation needs to be configured manually, this table shall support adding and deletion.
                All the links must locate on the two existing ports.
                "
            ::= { hwFrameLinks 2 }


        -- 1.3.6.1.4.1.2011.6.3.3.5.2.1
        hwFrameLinkEntry OBJECT-TYPE
            SYNTAX HwFrameLinkEntry
            MAX-ACCESS not-accessible
            STATUS current
            DESCRIPTION
                "
                The index of this entry is hwFrameLinkIndex.
                The frame link table. It describes the topology relation between the frames.
                For the device that can automatically discover the link relationship between the devices,
                this table can be implemented as read-only table. For the device whose inter-frame
                relation needs to be configured manually, this table shall support adding and deletion.
                All the links must locate on the two existing ports.
                "
            INDEX { hwFrameLinkIndex }
            ::= { hwFrameLinkTable 1 }


        HwFrameLinkEntry ::=
            SEQUENCE {
                hwFrameLinkIndex
                    Integer32,
                hwFrameLinkLeftFrame
                    Integer32,
                hwFrameLinkLeftSlot
                    Integer32,
                hwFrameLinkLeftSubSlot
                    Integer32,
                hwFrameLinkLeftPort
                    Integer32,
                hwFrameLinkRightFrame
                    Integer32,
                hwFrameLinkRightSlot
                    Integer32,
                hwFrameLinkRightSubSlot
                    Integer32,
                hwFrameLinkRightPort
                    Integer32,
                hwFrameLinkOperStatus
                    INTEGER,
                hwFrameLinkRowStatus
                    RowStatus
             }

        -- 1.3.6.1.4.1.2011.6.3.3.5.2.1.1
        hwFrameLinkIndex OBJECT-TYPE
            SYNTAX Integer32 (0..65535)
            MAX-ACCESS read-only
            STATUS current
            DESCRIPTION
                "
                Index of the frame link. It is sequentially numerated and exclusively identified in the device.
                There is no restriction to the coding rule.
                "
            ::= { hwFrameLinkEntry 1 }


        -- 1.3.6.1.4.1.2011.6.3.3.5.2.1.2
        hwFrameLinkLeftFrame OBJECT-TYPE
            SYNTAX Integer32
            MAX-ACCESS read-write
            STATUS current
            DESCRIPTION
                "
                The ID of the left node linked to the frame, corresponding to the hwFrameIndex in the hwFrameTable
                "
            ::= { hwFrameLinkEntry 2 }


        -- 1.3.6.1.4.1.2011.6.3.3.5.2.1.3
        hwFrameLinkLeftSlot OBJECT-TYPE
            SYNTAX Integer32
            MAX-ACCESS read-write
            STATUS current
            DESCRIPTION
                "
                The ID of the left slot linked to the frame, corresponding to the hwSlotIndex in the hwSlotTable.
                It indicates which slot of the left node is the link entry.
                "
            ::= { hwFrameLinkEntry 3 }


        -- 1.3.6.1.4.1.2011.6.3.3.5.2.1.4
        hwFrameLinkLeftSubSlot OBJECT-TYPE
            SYNTAX Integer32
            MAX-ACCESS read-write
            STATUS current
            DESCRIPTION
                "
                Link the left subslot, corresponding to the hwSubSlotIndex in the hwSubTable.
                It indicates which subslot of the left node is the link entry.
                "
            ::= { hwFrameLinkEntry 4 }


        -- 1.3.6.1.4.1.2011.6.3.3.5.2.1.5
        hwFrameLinkLeftPort OBJECT-TYPE
            SYNTAX Integer32
            MAX-ACCESS read-write
            STATUS current
            DESCRIPTION
                "
                The ID of the left port linked to the frame, corresponding to the hwPortIndex in the hwPortTable.
                It indicates which port of the left node is the link entry.
                "
            ::= { hwFrameLinkEntry 5 }


        -- 1.3.6.1.4.1.2011.6.3.3.5.2.1.6
        hwFrameLinkRightFrame OBJECT-TYPE
            SYNTAX Integer32
            MAX-ACCESS read-write
            STATUS current
            DESCRIPTION
                "
                The ID of the right node linked to the frame, corresponding to the hwFrameIndex of the hwFrameTable.
                "
            ::= { hwFrameLinkEntry 6 }


        -- 1.3.6.1.4.1.2011.6.3.3.5.2.1.7
        hwFrameLinkRightSlot OBJECT-TYPE
            SYNTAX Integer32
            MAX-ACCESS read-write
            STATUS current
            DESCRIPTION
                "
                The ID of the right slot linked the frame, corresponding to the hwSlotIndex of the hwSlotTable.
                It indicates which slot of the right node is the link entry.
                "
            ::= { hwFrameLinkEntry 7 }


        -- 1.3.6.1.4.1.2011.6.3.3.5.2.1.8
        hwFrameLinkRightSubSlot OBJECT-TYPE
            SYNTAX Integer32
            MAX-ACCESS read-write
            STATUS current
            DESCRIPTION
                "
                Link the right subslot, corresponding to the hwSubSlotIndex in the hwSubSlotTable.
                It indicates which subslot of the right node is the link entry.
                "
            ::= { hwFrameLinkEntry 8 }


        -- 1.3.6.1.4.1.2011.6.3.3.5.2.1.9
        hwFrameLinkRightPort OBJECT-TYPE
            SYNTAX Integer32
            MAX-ACCESS read-write
            STATUS current
            DESCRIPTION
                "
                The ID of the right port linked to the frame, corresponding to the hwPortIndex in the hwPortTable.
                It indicates which port of the right port is the link entry.
                "
            ::= { hwFrameLinkEntry 9 }


        -- 1.3.6.1.4.1.2011.6.3.3.5.2.1.10
        hwFrameLinkOperStatus OBJECT-TYPE
            SYNTAX INTEGER
                {
                normal(1),
                fault(2),
                discovery(3)
                }
            MAX-ACCESS read-only
            STATUS current
            DESCRIPTION
                "
                The running status of the link.
                Options:
                1.normal(1)    -  the running status of the link is normal
                2.fault(2)     -  the running status of the link is fault
                3.discovery(3) -  the link is discovered
                "
            ::= { hwFrameLinkEntry 10 }


        -- 1.3.6.1.4.1.2011.6.3.3.5.2.1.11
        hwFrameLinkRowStatus OBJECT-TYPE
            SYNTAX RowStatus
            MAX-ACCESS read-create
            STATUS current
            DESCRIPTION
                "
                The row status of the frame link, used to add or delete a link.
                "
            ::= { hwFrameLinkEntry 11 }


        -- 1.3.6.1.4.1.2011.6.3.3.5.3
        hwFrameLinkNextIndex OBJECT-TYPE
            SYNTAX Integer32 (0..254)
            MAX-ACCESS read-only
            STATUS current
            DESCRIPTION
                "
                The frame link table indicates adding the index value to be assigned by the new link.
                This leaf is used to access an index ID of the next frame link dynamically assigned by
                the host before delivering the adding link. To deliver the adding link,
                the value of the leaf shall be accessed,and be delivered together with the frame link table.
                Otherwise, the host can not execute the operation and will return the error.
                Default: 0
                "
            ::= { hwFrameLinks 3 }


        -- 1.3.6.1.4.1.2011.6.3.3.6
        hwNarrowBoard OBJECT IDENTIFIER ::= { hwSlotConf 6 }


        -- 1.3.6.1.4.1.2011.6.3.3.6.1
        hwBoardAttrTable OBJECT-TYPE
            SYNTAX SEQUENCE OF HwBoardAttrEntry
            MAX-ACCESS not-accessible
            STATUS current
            DESCRIPTION
                "
                Inquiring or modifying AULaw, impedance and current or ringvoltage of ASL, A32 and H511POTS ports.
                The indexes of this table are hwFrameIndex and hwSlotIndex.
                For the hwFrameIndex object, refer to hwFrameTable;
                for the hwSlotIndex object, refer to hwSlotTable.
                "
            ::= { hwNarrowBoard 1 }


        -- 1.3.6.1.4.1.2011.6.3.3.6.1.1
        hwBoardAttrEntry OBJECT-TYPE
            SYNTAX HwBoardAttrEntry
            MAX-ACCESS not-accessible
            STATUS current
            DESCRIPTION
                "
                Inquiring or modifying AULaw, impedance and current or ringvoltage of ASL, A32 and H511POTS ports.
                The indexes of this entry are hwFrameIndex and hwSlotIndex.
                For the hwFrameIndex object, refer to hwFrameTable;
                for the hwSlotIndex object, refer to hwSlotTable.
                "
            INDEX { hwFrameIndex, hwSlotIndex }
            ::= { hwBoardAttrTable 1 }


        HwBoardAttrEntry ::=
            SEQUENCE {
                hwBoardAulaw
                    Integer32,
                hwBoardCurrent
                    Integer32,
                hwBoardImpedance
                    Integer32,
                hwBoardEnvironment
                    INTEGER,
                hwBoardWorkmode
                    INTEGER,
                hwBoardRingVoltage
                    Integer32,
                hwBoardWorkState
                    INTEGER
                    }

        -- 1.3.6.1.4.1.2011.6.3.3.6.1.1.1
        hwBoardAulaw OBJECT-TYPE
            SYNTAX Integer32 (1..2)
            MAX-ACCESS read-write
            STATUS current
            DESCRIPTION
                "
                Coding method of voice signal when digitalizing.
                In different country or area it should be A law or u law.
                1    --    A law
                2    --    u law
                "
            ::= { hwBoardAttrEntry 1 }


        -- 1.3.6.1.4.1.2011.6.3.3.6.1.1.2
       hwBoardCurrent OBJECT-TYPE
            SYNTAX Integer32 (1..10)
            MAX-ACCESS read-write
            STATUS current
            DESCRIPTION
                "
                Port current supported by the board. The value ranges from 1 to 10,
                which indicates the port current value supported under certain loopline impedance.
                1    --    25mA steady current
                2    --    16mA steady current
                3    --    35mA 2*200
                4    --    35mA 2*250
                5    --    35mA 2*400
                6    --    47mA 2*200
                7    --    47mA 2*250
                8    --    47mA 2*400
                9    --    17mA steady current
                10   --   20mA steady current
                "
            ::= { hwBoardAttrEntry 2 }


        -- 1.3.6.1.4.1.2011.6.3.3.6.1.1.3
        hwBoardImpedance OBJECT-TYPE
            SYNTAX Integer32 (1..15 | 255)
            MAX-ACCESS read-write
            STATUS current
            DESCRIPTION
                "
                Port impedance of the board. The following values indicates different impedance with
                different application circumstances.
                1    --    Bureau machine in China(200+680|| 100nf)
                2    --    User Machine in China(200+560|| 100nf)
                3    --    600 Interface
                4    --    Interface of russian(150+510|| 47nf)
                5    --    (220+820|| 115nf )
                6    --    (220+820|| 120nf )
                7    --    900 Interface
                8    --    Interface of Brazil(800|| 50nf)
                9    --    BT(Zin=300+1000|| 220nf ,Zload=370+620|| 310nf)
                10   --    HK_BT3(Zin=370+620|| 310nf,Zload=600)
                11   --    HK_BT5(Zin=270+264|| 357nf+1434|| 265nf,Zload=600)
                12   --    BT1(BT0 without AGC)
                13   --    BT2(Zin=87+1052||228nF+229||28.4nF, Zload=270+264||357nF+1434||265nF)
                14   --    BT3(Zin=87+1052||228nF+229||28.4nF, Zload=164+162||363nF+1227||350nF)
                15   --    KPN(Zin= 270+750|| 150nf)
                255  --    Private definition
                "
            ::= { hwBoardAttrEntry 3 }


        -- 1.3.6.1.4.1.2011.6.3.3.6.1.1.4
        hwBoardEnvironment OBJECT-TYPE
            SYNTAX INTEGER
                {
                emsan(1),
                smsan(2)
                }
            MAX-ACCESS read-write
            STATUS current
            DESCRIPTION
                "
                The object is used to set and query the working environment of a board.
                Options:
                1.emsan(1) -indicates that the device is on a terminal node or a convergence node
                2.smsan(2) -indicates that the device is on a terminal node or a convergence node
                "
            DEFVAL { 1 }
            ::= { hwBoardAttrEntry 4 }


        -- 1.3.6.1.4.1.2011.6.3.3.6.1.1.5
        hwBoardWorkmode OBJECT-TYPE
            SYNTAX INTEGER
                {
                combo(1),
                powerSaving(2),
                auto(3)
                }
            MAX-ACCESS read-write
            STATUS current
            DESCRIPTION
                "
                The object is used to set the working mode of the COMBO board.
                Options:
                1.combo(1)       -the broadband and voice parts of the board are powered on
                2.powerSaving(2) -the board cuts off the power supply of the broadband part
                3.auto(3)        -normally the broadband and voice parts of the board are powered on
                                  When the mains supply is cut off, the board automatically cuts off
                                  the power supply of the broadband part
                "
            DEFVAL { 1 }
            ::= { hwBoardAttrEntry 5 }


        -- 1.3.6.1.4.1.2011.6.3.3.6.1.1.6
        hwBoardRingVoltage OBJECT-TYPE
            SYNTAX Integer32 (1..2)
            MAX-ACCESS read-write
            STATUS current
            DESCRIPTION
                "
                It is supported to config ringvoltage on virtual A04 board.
                It should be 41.5v or 45v.
                1    --    25Hz 41.5V
                2    --    25Hz 45V
                "
            ::= { hwBoardAttrEntry 6 }


--             DEFVAL { 1 }
        -- 1.3.6.1.4.1.2011.6.3.3.6.1.1.7
        hwBoardWorkState OBJECT-TYPE
            SYNTAX INTEGER
                {
                combo(1),
                powerSaving(2)
                }
            MAX-ACCESS read-only
            STATUS current
            DESCRIPTION
                "
                The object is used to query the working status of the COMBO board.
                Options:
                1. combo(1)       -if the broadband and voice parts of the board are powered on,
                                   the returned value is combo(1) ,DEFVAL { 1 }
                2. powerSaving(2) -if only the voice part of the board is powered on,
                                   the returned value is powerSaving(2)
                "
            ::= { hwBoardAttrEntry 7 }
        
	-- 1.3.6.1.4.1.2011.6.3.3.7
	hwVsPortTable OBJECT-TYPE
            SYNTAX SEQUENCE OF HwVsPortEntry
            MAX-ACCESS not-accessible
            STATUS current
            DESCRIPTION
                "Port query table that describes the detailed
                information of physical ports in the board, including the type,
                the virtual system mask of the port. 
                The indexes of this table are hwFrameIndex, hwSlotIndex, hwSubslotIndex and hwPortIndex.
                hwFrameIndex refer to hwFrameTable, hwSlotIndex refer to hwSlotTable,
                hwSubslotIndex refer to hwSubslotTable, hwPortIndex refer to hwPortTable.
                "
            ::= { hwSlotConf 7 }
			
	--1.3.6.1.4.1.2011.6.3.3.7.1
	hwVsPortEntry OBJECT-TYPE
            SYNTAX HwVsPortEntry
            MAX-ACCESS not-accessible
            STATUS current
            DESCRIPTION
                "Port query table that describes the detailed
                information of physical ports in the board, including the type,
                the virtual system mask of the port. 
                The indexes of this entry are hwFrameIndex, hwSlotIndex, hwSubslotIndex and hwPortIndex.
                hwFrameIndex refer to hwFrameTable, hwSlotIndex refer to hwSlotTable,
                hwSubslotIndex refer to hwSubslotTable, hwPortIndex refer to hwPortTable.
                "
            INDEX { hwFrameIndex, hwSlotIndex, hwSubslotIndex, hwPortIndex }
            ::= { hwVsPortTable 1 }
			
	HwVsPortEntry ::=
            SEQUENCE {
                hwVsPortType
                    HWPortType,
                hwVsPortVsMask
                    Integer32    
             }
			 
	-- 1.3.6.1.4.1.2011.6.3.3.7.1.1
        hwVsPortType OBJECT-TYPE
            SYNTAX HWPortType
            MAX-ACCESS read-only
            STATUS current
            DESCRIPTION
                "
                Port type, which is defined in HUAWEI-TC-MIB.mib.
                "
            ::= { hwVsPortEntry 1 }
			
	-- 1.3.6.1.4.1.2011.6.3.3.7.1.2
        hwVsPortVsMask OBJECT-TYPE
            SYNTAX Integer32
            MAX-ACCESS read-only
            STATUS current
            DESCRIPTION
                "
                The virtual system mask of the port, each bit indicates the VAN to which the port
                belongs. For example, the first bit maps vs0, the second bit maps vs1, and the rest 
                can be deducted by analog.
                 "
            ::= { hwVsPortEntry 2 }
            
        -- 1.3.6.1.4.1.2011.6.3.4
        hwCpuDevTable OBJECT-TYPE
            SYNTAX SEQUENCE OF HwCpuDevEntry
            MAX-ACCESS not-accessible
            STATUS current
            DESCRIPTION
                "
                The indexes of this table are hwFrameIndex, hwSlotIndex and hwCpuDevIndex.
                A table of CPU statistics.
                "
            ::= { hwDev 4 }


        -- 1.3.6.1.4.1.2011.6.3.4.1
        hwCpuDevEntry OBJECT-TYPE
            SYNTAX HwCpuDevEntry
            MAX-ACCESS not-accessible
            STATUS current
            DESCRIPTION
                "
                The indexes of this entry are hwFrameIndex, hwSlotIndex and hwCpuDevIndex.
                A table of CPU statistics.
                "
            INDEX { hwFrameIndex, hwSlotIndex, hwCpuDevIndex }
            ::= { hwCpuDevTable 1 }


        HwCpuDevEntry ::=
            SEQUENCE {
                hwCpuDevIndex
                    Integer32,
                hwCpuDevDuty
                    Integer32,
                hwAvgDuty1min
                    Integer32,
                hwAvgDuty5min
                    Integer32,
                hwCpuRunTime
                    Integer32,
                hwCpuOverLoadNum
                    Integer32,
                hwCpuOverLoadTime
                    Integer32,
                hwCpuCongestionNum
                    Integer32,
                hwCpuCongestionTime
                    Integer32
             }

        -- 1.3.6.1.4.1.2011.6.3.4.1.1
        hwCpuDevIndex OBJECT-TYPE
            SYNTAX Integer32 (0..255)
            MAX-ACCESS not-accessible
            STATUS current
            DESCRIPTION
                "
                CPU index, hwFrameIndex, and hwSlotIndex constitute the HUAWEI-CPU-MIB index. 
                For a single-CPU device, the value of this object is 0.
                "
            ::= { hwCpuDevEntry 1 }


        -- 1.3.6.1.4.1.2011.6.3.4.1.2
        hwCpuDevDuty OBJECT-TYPE
            SYNTAX Integer32 (0..100)
            MAX-ACCESS read-only
            STATUS current
            DESCRIPTION
                "
                The value of this object identifies the average CPU usage of a board or an entity.
                "
            ::= { hwCpuDevEntry 2 }


        -- 1.3.6.1.4.1.2011.6.3.4.1.3
        hwAvgDuty1min OBJECT-TYPE
            SYNTAX Integer32 (0..100)
            MAX-ACCESS read-only
            STATUS current
            DESCRIPTION
                "
                The value of this object identifies the average CPU usage of a board or entity 1 minute before the data is read.
                "
            ::= { hwCpuDevEntry 3 }


        -- 1.3.6.1.4.1.2011.6.3.4.1.4
        hwAvgDuty5min OBJECT-TYPE
            SYNTAX Integer32 (0..100)
            MAX-ACCESS read-only
            STATUS current
            DESCRIPTION
                "
                The value of this object identifies the average CPU usage of a board or entity 5 minutes before the data is read.
                "
            ::= { hwCpuDevEntry 4 }


        -- 1.3.6.1.4.1.2011.6.3.4.1.5
        hwCpuRunTime OBJECT-TYPE
            SYNTAX Integer32
            MAX-ACCESS read-only
            STATUS current
            DESCRIPTION
                "
                Duration of CPU running(s).
                "
            ::= { hwCpuDevEntry 5 }


        -- 1.3.6.1.4.1.2011.6.3.4.1.6
        hwCpuOverLoadNum OBJECT-TYPE
            SYNTAX Integer32
            MAX-ACCESS read-only
            STATUS current
            DESCRIPTION
                "
                Number of CPU overload.
                "
            ::= { hwCpuDevEntry 6 }


        -- 1.3.6.1.4.1.2011.6.3.4.1.7
        hwCpuOverLoadTime OBJECT-TYPE
            SYNTAX Integer32
            MAX-ACCESS read-only
            STATUS current
            DESCRIPTION
                "
                Duration of CPU overload(s).
                "
            ::= { hwCpuDevEntry 7 }


        -- 1.3.6.1.4.1.2011.6.3.4.1.8
        hwCpuCongestionNum OBJECT-TYPE
            SYNTAX Integer32
            MAX-ACCESS read-only
            STATUS current
            DESCRIPTION
                "
                Number of CPU congestion.
                "
            ::= { hwCpuDevEntry 8 }


        -- 1.3.6.1.4.1.2011.6.3.4.1.9
        hwCpuCongestionTime OBJECT-TYPE
            SYNTAX Integer32
            MAX-ACCESS read-only
            STATUS current
            DESCRIPTION
                "
                Duration of CPU congestion(s).
                "
            ::= { hwCpuDevEntry 9 }
        -- 1.3.6.1.4.1.2011.6.3.5
        hwMemoryDev OBJECT IDENTIFIER ::= { hwDev 5 }


        -- 1.3.6.1.4.1.2011.6.3.5.1
        hwMemoryDevTable OBJECT-TYPE
            SYNTAX SEQUENCE OF HwMemoryDevEntry
            MAX-ACCESS not-accessible
            STATUS current
            DESCRIPTION
                "
                The index of this table is hwFrameIndex, hwSlotIndex or hwMemoryDevModuleIndex.
                This table contains memory information.
                "
            ::= { hwMemoryDev 1 }


        -- 1.3.6.1.4.1.2011.6.3.5.1.1
        hwMemoryDevEntry OBJECT-TYPE
            SYNTAX HwMemoryDevEntry
            MAX-ACCESS not-accessible
            STATUS current
            DESCRIPTION
                "
                The index of this entry is hwFrameIndex, hwSlotIndex or hwMemoryDevModuleIndex.
                This table contains memory information.
                "
            INDEX { hwFrameIndex, hwSlotIndex, hwMemoryDevModuleIndex }
            ::= { hwMemoryDevTable 1 }


        HwMemoryDevEntry ::=
            SEQUENCE {
                hwMemoryDevModuleIndex
                    Integer32,
                hwMemoryDevSize
                    Unsigned32,
                hwMemoryDevFree
                    Unsigned32,
                hwMemoryDevRawSliceUsed
                    Unsigned32,
                hwMemoryDevLargestFree
                    Unsigned32,
                hwMemoryDevFail
                    Integer32,
                hwMemoryDevFailNoMem
                    Integer32,
                hwMemoryDevSize64
                    CounterBasedGauge64,
                hwMemoryDevFree64
                    CounterBasedGauge64
             }

        -- 1.3.6.1.4.1.2011.6.3.5.1.1.1
        hwMemoryDevModuleIndex OBJECT-TYPE
            SYNTAX Integer32 (0..65535)
            MAX-ACCESS not-accessible
            STATUS current
            DESCRIPTION
                "
                Index of hwMemoryDevTable.
                "
            ::= { hwMemoryDevEntry 1 }


        -- 1.3.6.1.4.1.2011.6.3.5.1.1.2
        hwMemoryDevSize OBJECT-TYPE
            SYNTAX Unsigned32
            MAX-ACCESS read-only
            STATUS current
            DESCRIPTION
                "
                Indicates the total size of the memory module
                which is on the managed object. Its unit is byte.
                "
            ::= { hwMemoryDevEntry 2 }


        -- 1.3.6.1.4.1.2011.6.3.5.1.1.3
        hwMemoryDevFree OBJECT-TYPE
            SYNTAX Unsigned32
            MAX-ACCESS read-only
            STATUS current
            DESCRIPTION
                "
                Indicates the free size of the memory, in the unit of byte.
                "
            ::= { hwMemoryDevEntry 3 }


        -- 1.3.6.1.4.1.2011.6.3.5.1.1.4
        hwMemoryDevRawSliceUsed OBJECT-TYPE
            SYNTAX Unsigned32
            MAX-ACCESS read-only
            STATUS current
            DESCRIPTION
                "
                Indicates the used size of the raw slice memory, in the unit of byte.
                "
            ::= { hwMemoryDevEntry 4 }


        -- 1.3.6.1.4.1.2011.6.3.5.1.1.5
        hwMemoryDevLargestFree OBJECT-TYPE
            SYNTAX Unsigned32
            MAX-ACCESS read-only
            STATUS current
            DESCRIPTION
                "
                The maximum size of the memory that can be currently used, in the unit of byte.
                "
            ::= { hwMemoryDevEntry 5 }


        -- 1.3.6.1.4.1.2011.6.3.5.1.1.6
        hwMemoryDevFail OBJECT-TYPE
            SYNTAX Integer32
            MAX-ACCESS read-only
            STATUS current
            DESCRIPTION
                "
                Count of memory allocation failures.
                "
            ::= { hwMemoryDevEntry 6 }


        -- 1.3.6.1.4.1.2011.6.3.5.1.1.7
        hwMemoryDevFailNoMem OBJECT-TYPE
            SYNTAX Integer32
            MAX-ACCESS read-only
            STATUS current
            DESCRIPTION
                "
                Count of the memory allocation
                "
            ::= { hwMemoryDevEntry 7 }


--  1.3.6.1.4.1.2011.6.3.5.1.1.8
        -- 1.3.6.1.4.1.2011.6.3.5.1.1.8
        hwMemoryDevSize64 OBJECT-TYPE
            SYNTAX CounterBasedGauge64
            MAX-ACCESS read-only
            STATUS current
            DESCRIPTION
                "
                Indicates the total size of the memory module incase of excessing 4G
                which is on the managed object.Its unit is byte.
                "
            ::= { hwMemoryDevEntry 8 }


--  1.3.6.1.4.1.2011.6.3.5.1.1.9
        -- 1.3.6.1.4.1.2011.6.3.5.1.1.9
        hwMemoryDevFree64 OBJECT-TYPE
            SYNTAX CounterBasedGauge64
            MAX-ACCESS read-only
            STATUS current
            DESCRIPTION
                "
                Indicates the free size of the memory incase of excessing 4G, in the unit of byte.
                "
            ::= { hwMemoryDevEntry 9 }


--  1.3.6.1.4.1.2011.6.3.5.2
        -- 1.3.6.1.4.1.2011.6.3.5.2
        hwBufferTable OBJECT-TYPE
            SYNTAX SEQUENCE OF HwBufferEntry
            MAX-ACCESS not-accessible
            STATUS current
            DESCRIPTION
                "
                The index of this table is hwFrameIndex, hwSlotIndex, hwBufferModuleIndex or hwBufferSize.
                Buffer  information table.
                "
            ::= { hwMemoryDev 2 }


        -- 1.3.6.1.4.1.2011.6.3.5.2.1
        hwBufferEntry OBJECT-TYPE
            SYNTAX HwBufferEntry
            MAX-ACCESS not-accessible
            STATUS current
            DESCRIPTION
                "
                The index of this entry is hwFrameIndex, hwSlotIndex, hwBufferModuleIndex or hwBufferSize.
                Buffer  information table.
                "
            INDEX { hwFrameIndex, hwSlotIndex, hwBufferModuleIndex, hwBufferSize }
            ::= { hwBufferTable 1 }


        HwBufferEntry ::=
            SEQUENCE {
                hwBufferModuleIndex
                    Integer32,
                hwBufferSize
                    Integer32,
                hwBufferCurrentTotal
                    Integer32,
                hwBufferCurrentUsed
                    Integer32
             }

        -- 1.3.6.1.4.1.2011.6.3.5.2.1.1
        hwBufferModuleIndex OBJECT-TYPE
            SYNTAX Integer32 (0..65535)
            MAX-ACCESS not-accessible
            STATUS current
            DESCRIPTION
                "
                Index of hwBufferTable.
                "
            ::= { hwBufferEntry 1 }


        -- 1.3.6.1.4.1.2011.6.3.5.2.1.2
        hwBufferSize OBJECT-TYPE
            SYNTAX Integer32 (1..65535)
            MAX-ACCESS not-accessible
            STATUS current
            DESCRIPTION
                "
                Contains the size of byte hwBuffers, in the unit of byte.
                "
            ::= { hwBufferEntry 2 }


        -- 1.3.6.1.4.1.2011.6.3.5.2.1.3
        hwBufferCurrentTotal OBJECT-TYPE
            SYNTAX Integer32
            MAX-ACCESS read-only
            STATUS current
            DESCRIPTION
                "
                Contains the total number of hwBuffers currently.
                "
            ::= { hwBufferEntry 3 }


        -- 1.3.6.1.4.1.2011.6.3.5.2.1.4
        hwBufferCurrentUsed OBJECT-TYPE
            SYNTAX Integer32
            MAX-ACCESS read-only
            STATUS current
            DESCRIPTION
                "
                Contains the number of used hwBuffers currently.
                "
            ::= { hwBufferEntry 4 }


        -- 1.3.6.1.4.1.2011.6.3.6
        hwFlashDev OBJECT IDENTIFIER ::= { hwDev 6 }


        -- 1.3.6.1.4.1.2011.6.3.6.1
        hwFlashDevTable OBJECT-TYPE
            SYNTAX SEQUENCE OF HwFlashDevEntry
            MAX-ACCESS not-accessible
            STATUS current
            DESCRIPTION
                "
                The index of this table is hwFrameIndex, hwSlotIndex or hwFlashDevIndex.
                This table contains flash information.
                "
            ::= { hwFlashDev 1 }


        -- 1.3.6.1.4.1.2011.6.3.6.1.1
        hwFlashDevEntry OBJECT-TYPE
            SYNTAX HwFlashDevEntry
            MAX-ACCESS not-accessible
            STATUS current
            DESCRIPTION
                "
                The index of this entry is hwFrameIndex, hwSlotIndex or hwFlashDevIndex.
                This table contains flash information.
                "
            INDEX { hwFrameIndex, hwSlotIndex, hwFlashDevIndex }
            ::= { hwFlashDevTable 1 }


        HwFlashDevEntry ::=
            SEQUENCE {
                hwFlashDevIndex
                    Integer32,
                hwFlashDevSize
                    Integer32,
                hwFlashDevFree
                    Integer32,
                hwFlashDevEraseTime
                    TimeTicks,
                hwFlashDevEraseStatus
                    INTEGER,
                hwFlashDevStatus
                    INTEGER
             }

        -- 1.3.6.1.4.1.2011.6.3.6.1.1.1
        hwFlashDevIndex OBJECT-TYPE
            SYNTAX Integer32 (0..65535)
            MAX-ACCESS not-accessible
            STATUS current
            DESCRIPTION
                "
                Index of hwFlashDevTable.
                "
            ::= { hwFlashDevEntry 1 }


        -- 1.3.6.1.4.1.2011.6.3.6.1.1.2
        hwFlashDevSize OBJECT-TYPE
            SYNTAX Integer32
            MAX-ACCESS read-only
            STATUS current
            DESCRIPTION
                "
                Total size in Octets of Flash memory,
                "
            ::= { hwFlashDevEntry 2 }


        -- 1.3.6.1.4.1.2011.6.3.6.1.1.3
        hwFlashDevFree OBJECT-TYPE
            SYNTAX Integer32
            MAX-ACCESS read-only
            STATUS current
            DESCRIPTION
                "
                Unused Size in Octets of Flash memory.
                "
            ::= { hwFlashDevEntry 3 }


        -- 1.3.6.1.4.1.2011.6.3.6.1.1.4
        hwFlashDevEraseTime OBJECT-TYPE
            SYNTAX TimeTicks
            MAX-ACCESS read-only
            STATUS current
            DESCRIPTION
                "
                The last time when Flash was erased after powerup.
                "
            DEFVAL { 0 }
            ::= { hwFlashDevEntry 4 }


        -- 1.3.6.1.4.1.2011.6.3.6.1.1.5
        hwFlashDevEraseStatus OBJECT-TYPE
            SYNTAX INTEGER
                {
                flashErasing(1),
                flashErasedSuccessful(2),
                flashErasedFail(3),
                flashReadOnly(4),
                flashOpenFailure(5),
                bufferAllocationFailure(6),
                noEraseAfterPowerOn(7)
                }
            MAX-ACCESS read-only
            STATUS current
            DESCRIPTION
                "
                Status of current or last flash erasing.
                Options:
                1.flashErasing(1)            -  flash is executing erasing operation
                2.flashErasedSuccessful(2)   -  flash erased successfully
                3.flashErasedFail(3)         -  flash erased failed
                4.flashReadOnly(4)           -  flash state is read only
                5.flashOpenFailure(5)        -  open flash failed
                6.bufferAllocationFailure(6) -  allocating buffer on flash failed
                7.noEraseAfterPowerOn(7)     -  there is no erasing operation after device was powered on
                "
            ::= { hwFlashDevEntry 5 }


        -- 1.3.6.1.4.1.2011.6.3.6.1.1.6
        hwFlashDevStatus OBJECT-TYPE
            SYNTAX INTEGER
                {
                busy(1),
                available(2)
                }
            MAX-ACCESS read-only
            STATUS current
            DESCRIPTION
                "
                Status of the availability of flash.
                Options:
                1.busy(1)       -  flash state is busy
                2.available(2)  -  flash state is available
                "
            ::= { hwFlashDevEntry 6 }


        -- 1.3.6.1.4.1.2011.6.3.7
        hwAlarmInfo OBJECT IDENTIFIER ::= { hwDev 7 }


        -- 1.3.6.1.4.1.2011.6.3.7.1
        hwAlarmTable OBJECT-TYPE
            SYNTAX SEQUENCE OF HwAlarmEntry
            MAX-ACCESS not-accessible
            STATUS obsolete
            DESCRIPTION
                "
                The index of this table is hwAlarmSerialIndex.
                This table is no longer used.
                "
            ::= { hwAlarmInfo 1 }


        -- 1.3.6.1.4.1.2011.6.3.7.1.1
        hwAlarmEntry OBJECT-TYPE
            SYNTAX HwAlarmEntry
            MAX-ACCESS not-accessible
            STATUS obsolete
            DESCRIPTION
                "
                The index of this entry is hwAlarmSerialIndex.
                This table is no longer used.
                "
            INDEX { hwAlarmSerialIndex }
            ::= { hwAlarmTable 1 }


        HwAlarmEntry ::=
            SEQUENCE {
                hwAlarmSerialIndex
                    Integer32,
                hwObsoleteAlarmType
                    INTEGER,
                hwAlarmOcurTime
                    DateAndTime,
                trapObjectIdValue
                    OCTET STRING
             }

        -- 1.3.6.1.4.1.2011.6.3.7.1.1.1
        hwAlarmSerialIndex OBJECT-TYPE
            SYNTAX Integer32 (0..2147483647)
            MAX-ACCESS read-only
            STATUS obsolete
            DESCRIPTION
                "
                This object is no longer used.
                "
            ::= { hwAlarmEntry 1 }


        -- 1.3.6.1.4.1.2011.6.3.7.1.1.2
        hwObsoleteAlarmType OBJECT-TYPE
            SYNTAX INTEGER
                {
                alarm(1),
                restore(2),
                event(3)
                }
            MAX-ACCESS read-only
            STATUS obsolete
            DESCRIPTION
                "
                The type of the Alarm.
                "
            ::= { hwAlarmEntry 2 }


        -- 1.3.6.1.4.1.2011.6.3.7.1.1.3
        hwAlarmOcurTime OBJECT-TYPE
            SYNTAX DateAndTime
            MAX-ACCESS read-only
            STATUS obsolete
            DESCRIPTION
                "
                This object is no longer used.
                "
            ::= { hwAlarmEntry 3 }


        -- 1.3.6.1.4.1.2011.6.3.7.1.1.4
        trapObjectIdValue OBJECT-TYPE
            SYNTAX OCTET STRING
            MAX-ACCESS read-only
            STATUS obsolete
            DESCRIPTION
                "
                This object is no longer used.
                "
            ::= { hwAlarmEntry 4 }


        -- 1.3.6.1.4.1.2011.6.3.8
        hwDevTraps OBJECT IDENTIFIER ::= { hwDev 8 }


        -- 1.3.6.1.4.1.2011.6.3.8.1
        hwDevTrapVbOids OBJECT IDENTIFIER ::= { hwDevTraps 1 }


        -- 1.3.6.1.4.1.2011.6.3.8.1.1
        hwFrameAdminResult OBJECT-TYPE
            SYNTAX INTEGER
                {
                success(1),
                fail(2)
                }
            MAX-ACCESS accessible-for-notify
            STATUS current
            DESCRIPTION
                "
                Frame administration result.
                "
            ::= { hwDevTrapVbOids 1 }


        -- 1.3.6.1.4.1.2011.6.3.8.1.2
        hwSlotAdminResult OBJECT-TYPE
            SYNTAX INTEGER
                {
                success(1),
                fail(2)
                }
            MAX-ACCESS accessible-for-notify
            STATUS current
            DESCRIPTION
                "
                Slot administration result.
                "
            ::= { hwDevTrapVbOids 2 }


        -- 1.3.6.1.4.1.2011.6.3.8.1.3
        hwSubslotAdminResult OBJECT-TYPE
            SYNTAX INTEGER
                {
                success(1),
                fail(2)
                }
            MAX-ACCESS accessible-for-notify
            STATUS current
            DESCRIPTION
                "
                Subslot administration result.
                "
            ::= { hwDevTrapVbOids 3 }


        -- 1.3.6.1.4.1.2011.6.3.8.1.4
        hwPortAdminResult OBJECT-TYPE
            SYNTAX INTEGER
                {
                success(1),
                fail(2)
                }
            MAX-ACCESS accessible-for-notify
            STATUS current
            DESCRIPTION
                "
                Port administration result.
                "
            ::= { hwDevTrapVbOids 4 }


        -- 1.3.6.1.4.1.2011.6.3.8.1.5
        hwConfigChangeIP OBJECT-TYPE
            SYNTAX IpAddress
            MAX-ACCESS accessible-for-notify
            STATUS current
            DESCRIPTION
                "
                The serial IP of configuration changes.
                If the configuration changes is trigger by the command line users, the IP address is 0.0.0.0.
                If it is triggered by the SNMP user, the IP address is the SNMP user's IP address.
                The Trap of configuration changes will not be sent to the SNMP user,
                who triggered the configuration changes.
                "
            ::= { hwDevTrapVbOids 5 }


        -- 1.3.6.1.4.1.2011.6.3.8.1.6
        hwDevUserLabelType OBJECT-TYPE
            SYNTAX Integer32
            MAX-ACCESS accessible-for-notify
            STATUS current
            DESCRIPTION
                "
                User label type.
                1. Frame type.
                2. Slot type.
                3. Port type.
                "
            ::= { hwDevTrapVbOids 6 }


        -- 1.3.6.1.4.1.2011.6.3.8.1.7
        hwDevUserLabel OBJECT-TYPE
            SYNTAX OCTET STRING
            MAX-ACCESS accessible-for-notify
            STATUS current
            DESCRIPTION
                "
                User label.
                "
            ::= { hwDevTrapVbOids 7 }


        -- 1.3.6.1.4.1.2011.6.3.8.1.8
        hwDevVPI OBJECT-TYPE
            SYNTAX Integer32
            MAX-ACCESS accessible-for-notify
            STATUS current
            DESCRIPTION
                "
                This node is reserved and has no actual meaning.
                "
            ::= { hwDevTrapVbOids 8 }


        -- 1.3.6.1.4.1.2011.6.3.8.1.9
        hwDevVCI OBJECT-TYPE
            SYNTAX Integer32
            MAX-ACCESS accessible-for-notify
            STATUS current
            DESCRIPTION
                "
                This node is reserved and has no actual meaning.
                "
            ::= { hwDevTrapVbOids 9 }


        -- 1.3.6.1.4.1.2011.6.3.8.1.10
        hwDevVlanId OBJECT-TYPE
            SYNTAX Integer32
            MAX-ACCESS accessible-for-notify
            STATUS current
            DESCRIPTION
                "
                This node is reserved and has no actual meaning.
                "
            ::= { hwDevTrapVbOids 10 }


        -- 1.3.6.1.4.1.2011.6.3.8.1.11
        hwFrameTypeConfigured OBJECT-TYPE
            SYNTAX HWFrameType
            MAX-ACCESS accessible-for-notify
            STATUS current
            DESCRIPTION
                "
                Type of the frame that is configured in database of device.
                "
            ::= { hwDevTrapVbOids 11 }


        -- 1.3.6.1.4.1.2011.6.3.8.1.12
        hwActualSlotTypeName OBJECT-TYPE
            SYNTAX OCTET STRING (SIZE (0..64))
            MAX-ACCESS accessible-for-notify
            STATUS current
            DESCRIPTION
                "
                Type and name of the inserted board.
                "
            ::= { hwDevTrapVbOids 12 }


        -- 1.3.6.1.4.1.2011.6.3.8.1.13
        hwOldDeviceIpAddr OBJECT-TYPE
            SYNTAX IpAddress
            MAX-ACCESS accessible-for-notify
            STATUS current
            DESCRIPTION
                "
                Old IP address of the device.
                "
            ::= { hwDevTrapVbOids 13 }


        -- 1.3.6.1.4.1.2011.6.3.8.1.14
        hwNewDeviceIpAddr OBJECT-TYPE
            SYNTAX IpAddress
            MAX-ACCESS accessible-for-notify
            STATUS current
            DESCRIPTION
                "
                New IP address of the device.
                "
            ::= { hwDevTrapVbOids 14 }


        -- 1.3.6.1.4.1.2011.6.3.8.1.15
        hwOldSubslotType0 OBJECT-TYPE
            SYNTAX HWSubPCBType
            MAX-ACCESS accessible-for-notify
            STATUS current
            DESCRIPTION
                "
                Type of the first daughter board that is used previously.
                "
            ::= { hwDevTrapVbOids 15 }


        -- 1.3.6.1.4.1.2011.6.3.8.1.16
        hwOldSubslotType1 OBJECT-TYPE
            SYNTAX HWSubPCBType
            MAX-ACCESS accessible-for-notify
            STATUS current
            DESCRIPTION
                "
                Type of the second daughter board that is used previously.
                "
            ::= { hwDevTrapVbOids 16 }


        -- 1.3.6.1.4.1.2011.6.3.8.1.17
        hwOldSubslotType2 OBJECT-TYPE
            SYNTAX HWSubPCBType
            MAX-ACCESS accessible-for-notify
            STATUS current
            DESCRIPTION
                "
                Type of the third daughter board that is used previously.
                "
            ::= { hwDevTrapVbOids 17 }


        -- 1.3.6.1.4.1.2011.6.3.8.1.18
        hwOldSubslotType3 OBJECT-TYPE
            SYNTAX HWSubPCBType
            MAX-ACCESS accessible-for-notify
            STATUS current
            DESCRIPTION
                "
                Type of the fourth daughter board that is used previously.
                "
            ::= { hwDevTrapVbOids 18 }


        -- 1.3.6.1.4.1.2011.6.3.8.1.19
        hwDevStandbyMainSlotTypeName OBJECT-TYPE
            SYNTAX OCTET STRING
            MAX-ACCESS accessible-for-notify
            STATUS current
            DESCRIPTION
                "
                Slot information description, to describe standby main board name information of the slot.
                "
            ::= { hwDevTrapVbOids 19 }


        -- 1.3.6.1.4.1.2011.6.3.8.1.20
        hwDevConfPreviousTable OBJECT-TYPE
            SYNTAX SEQUENCE OF HwDevConfPreviousEntry
            MAX-ACCESS not-accessible
            STATUS current
            DESCRIPTION
                "
                Previous Device querying table. It is used to query barcode and name of previous device
                which was replaced by a new one.
                The indexes of this table are hwFrameIndex and hwSlotIndex.
                "
            ::= { hwDevTrapVbOids 20 }


        -- 1.3.6.1.4.1.2011.6.3.8.1.20.1
        hwDevConfPreviousEntry OBJECT-TYPE
            SYNTAX HwDevConfPreviousEntry
            MAX-ACCESS not-accessible
            STATUS current
            DESCRIPTION
                "
                Previous Device querying table. It is used to query barcode and name of previous device
                which was replaced by a new one.
                The indexes of this entry are hwFrameIndex and hwSlotIndex.
                "
            INDEX { hwFrameIndex, hwSlotIndex }
            ::= { hwDevConfPreviousTable 1 }


        HwDevConfPreviousEntry ::=
            SEQUENCE {
                hwDevPreSlotTypeName
                    OCTET STRING,
                hwDevPreSlotPhySerialNum
                    OCTET STRING
             }

        -- 1.3.6.1.4.1.2011.6.3.8.1.20.1.1
        hwDevPreSlotTypeName OBJECT-TYPE
            SYNTAX OCTET STRING
            MAX-ACCESS accessible-for-notify
            STATUS current
            DESCRIPTION
                "
                Slot information description, to describe previous board name information of the slot.
                The indexes of the entry are hwFrameIndex and hwSlotIndex.
                "
            ::= { hwDevConfPreviousEntry 1 }


        -- 1.3.6.1.4.1.2011.6.3.8.1.20.1.2
        hwDevPreSlotPhySerialNum OBJECT-TYPE
            SYNTAX OCTET STRING
            MAX-ACCESS accessible-for-notify
            STATUS current
            DESCRIPTION
                "
                The vendor-specific serial number string for the previous board of the slot.
                The preferred value is the serial number string actually printed on the component itself.
                The indices of the entry are hwFrameIndex and hwSlotIndex.
                "
            ::= { hwDevConfPreviousEntry 2 }


        -- 1.3.6.1.4.1.2011.6.3.8.1.21
        hwSystemResParaTable OBJECT-TYPE
            SYNTAX SEQUENCE OF HwSystemResParaEntry
            MAX-ACCESS not-accessible
            STATUS current
            DESCRIPTION
                "
                The index of this table is hwResTypePara. System resource table.
                "
            ::= { hwDevTrapVbOids 21 }


        -- 1.3.6.1.4.1.2011.6.3.8.1.21.1
        hwSystemResParaEntry OBJECT-TYPE
            SYNTAX HwSystemResParaEntry
            MAX-ACCESS not-accessible
            STATUS current
            DESCRIPTION
                "
                The index of this entry is hwResTypePara. System resource table.
                "
            INDEX { hwResTypePara }
            ::= { hwSystemResParaTable 1 }


        HwSystemResParaEntry ::=
            SEQUENCE {
                hwResTypePara
                    INTEGER,
                hwResOccupancyPara
                    Integer32
             }

        -- 1.3.6.1.4.1.2011.6.3.8.1.21.1.1
        hwResTypePara OBJECT-TYPE
            SYNTAX INTEGER
                {
                memory(1),
                messageUnits(2),
                cpu(3)
                }
            MAX-ACCESS accessible-for-notify
            STATUS current
            DESCRIPTION
                "
                System resource type.
                Options:
                1. memory(1)      -indicates the memory resource
                2. messageUnits(2)-indicates the message resource
                3. cpu(3)         -indicates the CPU resource
                "
            ::= { hwSystemResParaEntry 1 }


        -- 1.3.6.1.4.1.2011.6.3.8.1.21.1.2
        hwResOccupancyPara OBJECT-TYPE
            SYNTAX Integer32 (0..100)
            MAX-ACCESS accessible-for-notify
            STATUS current
            DESCRIPTION
                "
                System resource occupancy.
                "
            ::= { hwSystemResParaEntry 2 }


        -- 1.3.6.1.4.1.2011.6.3.8.1.22
        hwTrapStorageName OBJECT-TYPE
            SYNTAX OCTET STRING
            MAX-ACCESS accessible-for-notify
            STATUS current
            DESCRIPTION
                "
                The first para of storage fault, which describe the storage name.
                "
            ::= { hwDevTrapVbOids 22 }


        -- 1.3.6.1.4.1.2011.6.3.8.1.23
        hwExtendBoardFrameIndex OBJECT-TYPE
            SYNTAX Integer32
            MAX-ACCESS accessible-for-notify
            STATUS current
            DESCRIPTION
                "
                The frame index of the port connecting the main frame to the extended frame.
                "
            ::= { hwDevTrapVbOids 23 }


        -- 1.3.6.1.4.1.2011.6.3.8.1.24
        hwExtendedFrameUplinkPort OBJECT-TYPE
            SYNTAX Integer32
            MAX-ACCESS accessible-for-notify
            STATUS current
            DESCRIPTION
                "
                Another uplink port of extended frame.
                "
            ::= { hwDevTrapVbOids 24 }


        -- 1.3.6.1.4.1.2011.6.3.8.1.25
        hwExtendBoardSlotIndex OBJECT-TYPE
            SYNTAX Integer32
            MAX-ACCESS accessible-for-notify
            STATUS current
            DESCRIPTION
                "
                The slot index of the port connecting the main frame to the extended frame.
                "
            ::= { hwDevTrapVbOids 25 }


        -- 1.3.6.1.4.1.2011.6.3.8.1.26
        hwExtendBoardPortIndex OBJECT-TYPE
            SYNTAX Integer32
            MAX-ACCESS accessible-for-notify
            STATUS current
            DESCRIPTION
                "
                The port index of the port connecting the main frame to the extended frame.
                "
            ::= { hwDevTrapVbOids 26 }


        -- 1.3.6.1.4.1.2011.6.3.8.1.27
        hwTrapHardFaultName OBJECT-TYPE
            SYNTAX OCTET STRING
            MAX-ACCESS accessible-for-notify
            STATUS current
            DESCRIPTION
                "
                The name of board hard fault.
                "
            ::= { hwDevTrapVbOids 27 }


        -- 1.3.6.1.4.1.2011.6.3.8.1.28
        hwTrapHardFaultEffect OBJECT-TYPE
            SYNTAX OCTET STRING
            MAX-ACCESS accessible-for-notify
            STATUS current
            DESCRIPTION
                "
                The effect of board hard fault.
                "
            ::= { hwDevTrapVbOids 28 }


        -- 1.3.6.1.4.1.2011.6.3.8.1.29
        hwSlotInputIdIndex OBJECT-TYPE
            SYNTAX Integer32 (0..255)
            MAX-ACCESS accessible-for-notify
            STATUS current
            DESCRIPTION
                "
                Input Circuit Index.
                "
            ::= { hwDevTrapVbOids 29 }


        -- 1.3.6.1.4.1.2011.6.3.8.1.30
        hwSlotInputType OBJECT-TYPE
            SYNTAX INTEGER
                {
                localac(1),
                localdc(2),
                remoteac(3),
                remotedc(4),
                pd(5)
                }
            MAX-ACCESS accessible-for-notify
            STATUS current
            DESCRIPTION
                "
                Voltage Input Type.
                Options:
                1. localac(1)   -local ac type.
                2. localdc(2)   -local dc type.
                3. remoteac(3)  -remote ac type.
                4. remotedc(4)  -remote dc type.
                5. pd(5)        -pd type.
                "
            ::= { hwDevTrapVbOids 30 }


        -- 1.3.6.1.4.1.2011.6.3.8.1.31
        hwDevAutoDeployPhase OBJECT-TYPE
            SYNTAX DisplayString
            MAX-ACCESS accessible-for-notify
            STATUS current
            DESCRIPTION
                "
                Auto-deployment phase:
                1. Download the auto-deployment policy file
                2. Parse the auto-deployment policy file
                3. Download the upgrade software
                4. Download the configuration file
                5. Download common configuration scripts
                6. Download customized configuration scripts
                7. Issue the automatic backup configuration
                8. Download the database
                9. Save the database and configuration file
                "
            ::= { hwDevTrapVbOids 31 }


        -- 1.3.6.1.4.1.2011.6.3.8.1.32
        hwVccLocalChassisId OBJECT-TYPE
            SYNTAX Unsigned32
            MAX-ACCESS accessible-for-notify
            STATUS current
            DESCRIPTION
            	"
            	The index of local chassis.
            	"
            ::= { hwDevTrapVbOids 32 }

        -- 1.3.6.1.4.1.2011.6.3.8.1.33
        hwVccNeighbourChassisId OBJECT-TYPE
            SYNTAX Unsigned32
            MAX-ACCESS accessible-for-notify
            STATUS current
            DESCRIPTION
            	"
            	The index of neighbour chassis.
            	"
            ::= { hwDevTrapVbOids 33 }

        -- 1.3.6.1.4.1.2011.6.3.8.1.34
        hwVccGroupId OBJECT-TYPE
            SYNTAX Unsigned32
            MAX-ACCESS accessible-for-notify
            STATUS current
            DESCRIPTION
            	"
            	The index of data channel.
            	"
            ::= { hwDevTrapVbOids 34 }

        -- 1.3.6.1.4.1.2011.6.3.8.1.35
        hwVccLinkIfPhysicIndex OBJECT-TYPE
            SYNTAX Unsigned32
            MAX-ACCESS accessible-for-notify
            STATUS current
            DESCRIPTION
            	"
            	The index of interface for the data link.
            	"
            ::= { hwDevTrapVbOids 35 }

        -- 1.3.6.1.4.1.2011.6.3.8.1.36
        hwVccLinkIfPhysicName OBJECT-TYPE
            SYNTAX OCTET STRING
            MAX-ACCESS accessible-for-notify
            STATUS current
            DESCRIPTION
            	"
            	The name of interface for the data link.
            	"
            ::= { hwDevTrapVbOids 36 }

        -- 1.3.6.1.4.1.2011.6.3.8.1.37
        hwTrapPowerPortIndex OBJECT-TYPE
            SYNTAX Integer32
            MAX-ACCESS accessible-for-notify
            STATUS current
            DESCRIPTION
            	"
            	The index of power port.
            	"
            ::= { hwDevTrapVbOids 37 }  
            
        -- 1.3.6.1.4.1.2011.6.3.8.1.38
        hwDevTempMinorAlmThreshold OBJECT-TYPE
            SYNTAX OCTET STRING
            MAX-ACCESS accessible-for-notify
            STATUS current
            DESCRIPTION
            	"
            	The level-1 high temperature alarm threshold.
            	"
            ::= { hwDevTrapVbOids 38 }

        -- 1.3.6.1.4.1.2011.6.3.8.1.39
        hwDevTempMajorAlmThreshold OBJECT-TYPE
            SYNTAX OCTET STRING
            MAX-ACCESS accessible-for-notify
            STATUS current
            DESCRIPTION
            	"
            	The level-2 high temperature alarm threshold.
            	"
            ::= { hwDevTrapVbOids 39 } 
            
        -- 1.3.6.1.4.1.2011.6.3.8.1.40
        hwDevTempCriticalAlmThreshold OBJECT-TYPE
            SYNTAX OCTET STRING
            MAX-ACCESS accessible-for-notify
            STATUS current
            DESCRIPTION
            	"
            	The level-3 high temperature alarm threshold.
            	"
            ::= { hwDevTrapVbOids 40 }
                                        
        -- 1.3.6.1.4.1.2011.6.3.8.1.41
        hwDeviceCurrentTemp OBJECT-TYPE
            SYNTAX OCTET STRING
            MAX-ACCESS accessible-for-notify
            STATUS current
            DESCRIPTION
            	"
            	The current temperature of the device.
            	"
            ::= { hwDevTrapVbOids 41 }                                

        -- 1.3.6.1.4.1.2011.6.3.8.1.42       
        hwDevSnmpHostIpAddress OBJECT-TYPE           
            SYNTAX InetAddress
            MAX-ACCESS accessible-for-notify
            STATUS current
            DESCRIPTION
                "
                The IP address of SNMP probe abnormal record.
                "
            ::= { hwDevTrapVbOids 42 } 
                                           
        -- 1.3.6.1.4.1.2011.6.3.8.1.43        
        hwDevSnmpLastReceivedTime OBJECT-TYPE           
            SYNTAX DateAndTime
            MAX-ACCESS accessible-for-notify
            STATUS current
            DESCRIPTION
                "
                The last probe time of SNMP probe abnormal record.
                "
            ::= { hwDevTrapVbOids 43 }
            
        -- 1.3.6.1.4.1.2011.6.3.8.1.44       
        hwDevSnmpAverageInterval OBJECT-TYPE           
            SYNTAX Integer32
            MAX-ACCESS accessible-for-notify
            STATUS current
            DESCRIPTION
                "
                The average interval of SNMP probe abnormal record.
                "
            ::= { hwDevTrapVbOids 44 }

        -- 1.3.6.1.4.1.2011.6.3.8.1.45       
        hwDevSnmpMinimumInterval OBJECT-TYPE           
            SYNTAX Integer32
            MAX-ACCESS accessible-for-notify
            STATUS current
            DESCRIPTION
                "
                The minimum interval of SNMP probe abnormal record.
                "
            ::= { hwDevTrapVbOids 45 }
            
        -- 1.3.6.1.4.1.2011.6.3.8.1.46       
        hwDevSnmpMaxmumInterval OBJECT-TYPE           
            SYNTAX Integer32
            MAX-ACCESS accessible-for-notify
            STATUS current
            DESCRIPTION
                "
                The maxmum interval of SNMP probe abnormal record.
                "
            ::= { hwDevTrapVbOids 46 }
                                          
        -- 1.3.6.1.4.1.2011.6.3.8.1.47      
        hwDevSnmpReceivedCount OBJECT-TYPE           
            SYNTAX Integer32
            MAX-ACCESS accessible-for-notify
            STATUS current
            DESCRIPTION
                "
                The connection count of SNMP probe abnormal record.
                "
            ::= { hwDevTrapVbOids 47 }
                                                    
        -- 1.3.6.1.4.1.2011.6.3.8.1.48      
        hwSubboardID OBJECT-TYPE           
            SYNTAX Integer32
            MAX-ACCESS accessible-for-notify
            STATUS current
            DESCRIPTION
                "
                The index ID of sub board.
                "
            ::= { hwDevTrapVbOids 48 }
			
        -- 1.3.6.1.4.1.2011.6.3.8.2
        hwDevCommonTraps OBJECT IDENTIFIER ::= { hwDevTraps 2 }


        -- 1.3.6.1.4.1.2011.6.3.8.2.0
        hwDevCommonTrapsPrefix OBJECT IDENTIFIER ::= { hwDevCommonTraps 0 }


        -- 1.3.6.1.4.1.2011.6.3.8.2.0.1
        hwDevBoardDetectTrap NOTIFICATION-TYPE
            OBJECTS { hwFrameIndex, hwSlotIndex, hwSlotType, hwSlotOperStatus, hwSlotTypeName,
                hwSlotPrimaryStatus, hwSlotSecondaryStatus }
            STATUS current
            DESCRIPTION
                "
                This trap message is reported when a board is detected.
                "
            ::= { hwDevCommonTrapsPrefix 1 }


        -- 1.3.6.1.4.1.2011.6.3.8.2.0.2
        hwDevBoardDisappearedTrap NOTIFICATION-TYPE
            OBJECTS { hwFrameIndex, hwSlotIndex, hwSlotType, hwSlotTypeName }
            STATUS current
            DESCRIPTION
                "
                This trap message is reported when a board disappears.
                "
            ::= { hwDevCommonTrapsPrefix 2 }


        -- 1.3.6.1.4.1.2011.6.3.8.2.0.3
        hwDevBoardStateChangedTrap NOTIFICATION-TYPE
            OBJECTS { hwFrameIndex, hwSlotIndex, hwSlotType, hwSlotOperStatus, hwSlotPrimaryStatus,
                hwSlotSecondaryStatus }
            STATUS current
            DESCRIPTION
                "
                This trap message is reported when a board's state changes.
                "
            ::= { hwDevCommonTrapsPrefix 3 }


        -- 1.3.6.1.4.1.2011.6.3.8.2.0.4
        hwDevBoardStaChgOffLineTrap NOTIFICATION-TYPE
            OBJECTS { hwFrameIndex, hwSlotIndex, hwSlotType, hwSlotOperStatus, hwSlotPrimaryStatus,
                hwSlotSecondaryStatus }
            STATUS current
            DESCRIPTION
                "
                This trap message is reported when a board's state changes from online to offline.
                "
            ::= { hwDevCommonTrapsPrefix 4 }


        -- 1.3.6.1.4.1.2011.6.3.8.2.0.5
        hwDevBoardAutoLoadTrap NOTIFICATION-TYPE
            OBJECTS { hwFrameIndex, hwSlotIndex, hwSlotType, hwSlotOperStatus, hwSlotTypeName
                 }
            STATUS current
            DESCRIPTION
                "
                This trap message is reported when a board starts to autoload.
                "
            ::= { hwDevCommonTrapsPrefix 5 }


        -- 1.3.6.1.4.1.2011.6.3.8.2.0.6
        hwDevUserlabelChangeTrap NOTIFICATION-TYPE
            OBJECTS { hwConfigChangeIP, hwDevUserLabelType, hwDevUserLabel, hwFrameIndex, hwSlotIndex,
                hwSubslotIndex, hwPortIndex, hwDevVPI, hwDevVCI, hwDevVlanId
                 }
            STATUS current
            DESCRIPTION
                "
                This trap message is reported when a board's userlabel changes.
                The binding parameters hwDevVPI, hwDevVCI and hwDevVlanId are reserved and have no actual meaning.
                "
            ::= { hwDevCommonTrapsPrefix 6 }


        -- 1.3.6.1.4.1.2011.6.3.8.2.0.7
        hwDevSystemStateChangeTrap NOTIFICATION-TYPE
            OBJECTS { hwSystemPrimaryStatus }
            STATUS current
            DESCRIPTION
                "This trap message is reported when the system state changes."
            ::= { hwDevCommonTrapsPrefix 7 }


        -- 1.3.6.1.4.1.2011.6.3.8.2.0.8
        hwDevFrameDetectTrap NOTIFICATION-TYPE
            OBJECTS { hwFrameIndex, hwFrameType, hwFrameExtendPort, hwFrameUplinkPort, hwFrameOperStatus,
                hwFrameTypeName }
            STATUS current
            DESCRIPTION
                "
                This trap message is reported when a frame is detected.
                "
            ::= { hwDevCommonTrapsPrefix 8 }


        -- 1.3.6.1.4.1.2011.6.3.8.2.0.9
        hwDevFrameDisappearedTrap NOTIFICATION-TYPE
            OBJECTS { hwFrameIndex, hwFrameType, hwFrameExtendPort, hwFrameUplinkPort, hwFrameTypeName
                 }
            STATUS current
            DESCRIPTION
                "
                This trap message is reported when a frame disappears.
                "
            ::= { hwDevCommonTrapsPrefix 9 }


        -- 1.3.6.1.4.1.2011.6.3.8.2.0.10
        hwDevFrameStateChangeTrap NOTIFICATION-TYPE
            OBJECTS { hwFrameIndex, hwFrameType, hwFrameOperStatus, hwFrameExtendPort, hwFrameUplinkPort
                 }
            STATUS current
            DESCRIPTION
                "
                This trap message is reported when a frame's state changes.
                "
            ::= { hwDevCommonTrapsPrefix 10 }


        -- 1.3.6.1.4.1.2011.6.3.8.2.0.11
        hwDevExtendedFramePortChangeTrap NOTIFICATION-TYPE
            OBJECTS { hwFrameIndex, hwFrameType, hwFrameUplinkPort, hwExtendedFrameUplinkPort }
            STATUS current
            DESCRIPTION
                "
                This trap message is reported when a extended frame's uplink port changes.
                "
            ::= { hwDevCommonTrapsPrefix 11 }
            
        -- 1.3.6.1.4.1.2011.6.3.8.2.0.12        
        hwDevSnmpProbeRecordTrap NOTIFICATION-TYPE           
            OBJECTS { hwDevSnmpHostIpAddress, hwDevSnmpLastReceivedTime, hwDevSnmpAverageInterval, hwDevSnmpMinimumInterval, hwDevSnmpMaxmumInterval, hwDevSnmpReceivedCount }
            STATUS current
            DESCRIPTION
                "
                This trap message is reported when the abnormal record of SNMP probe monitor occurs.
                "
            ::= { hwDevCommonTrapsPrefix 12 }


-- 1.3.6.1.4.1.2011.6.3.8.3
        hwDevAlarmTraps OBJECT IDENTIFIER ::= { hwDevTraps 3 }


-- 1.3.6.1.4.1.2011.6.3.8.3.1
        hwDevSystemTraps OBJECT IDENTIFIER ::= { hwDevAlarmTraps 1 }


-- 1.3.6.1.4.1.2011.6.3.8.3.1.0
        -- 1.3.6.1.4.1.2011.6.3.8.3.1.0
        hwDevSystemTrapsPrefix OBJECT IDENTIFIER ::= { hwDevSystemTraps 0 }


        -- 1.3.6.1.4.1.2011.6.3.8.3.1.0.2
        hwDevSystemDataSynCancelTrap NOTIFICATION-TYPE
            OBJECTS { hwFrameIndex, hwSlotIndex, hwSlotIndex }
            STATUS current
            DESCRIPTION
                "
                This trap message is reported when the data synchronization
                between the active and standby control boards is canceled.
                The first hwSlotIndex indicates active main board index,
                the second hwSlotIndex indicates standby main board index.
                "
            ::= { hwDevSystemTrapsPrefix 2 }


        -- 1.3.6.1.4.1.2011.6.3.8.3.1.0.3
        hwDevActiveStandbyContolBoardInconsistentTrap NOTIFICATION-TYPE
            OBJECTS { hwSlotTypeName, hwDevStandbyMainSlotTypeName }
            STATUS current
            DESCRIPTION
                "
                This trap message is reported when the active control board type
                is inconsistent with standby ctrol board type.
                "
            ::= { hwDevSystemTrapsPrefix 3 }


        -- 1.3.6.1.4.1.2011.6.3.8.3.1.0.5
        hwDevActiveStandbyDataSynCancelTrap NOTIFICATION-TYPE
            OBJECTS { hwFrameIndex, hwSlotIndex, hwSlotIndex }
            STATUS current
            DESCRIPTION
                "
                This trap message is reported when the data synchronization
                between the active and standby control boards is canceled.
                The first hwSlotIndex indicates active main board index,
                the second hwSlotIndex indicates standby main board index.
                "
            ::= { hwDevSystemTrapsPrefix 5 }


        -- 1.3.6.1.4.1.2011.6.3.8.3.1.0.6
        hwDevActiveStandbyDataSynCancelRecoverTrap NOTIFICATION-TYPE
            OBJECTS { hwFrameIndex, hwSlotIndex, hwSlotIndex }
            STATUS current
            DESCRIPTION
                "
                This trap message is reported when the data synchronization
                between the active and standby control boards recovers.
                The first hwSlotIndex indicates active main board index,
                the second hwSlotIndex indicates standby main board index.
                "
            ::= { hwDevSystemTrapsPrefix 6 }


        -- 1.3.6.1.4.1.2011.6.3.8.3.1.0.7
        hwDevSystemPoweroffTrap NOTIFICATION-TYPE
            STATUS current
            DESCRIPTION
                "
                This trap message is reported when the device is cut off.
                "
            ::= { hwDevSystemTrapsPrefix 7 }


        -- 1.3.6.1.4.1.2011.6.3.8.3.1.0.8
        hwDevSystemAutoDeployFailTrap NOTIFICATION-TYPE
            OBJECTS { hwDevAutoDeployPhase }
            STATUS current
            DESCRIPTION
                "
                This trap message is reported when the auto-deployment fails.
                "
            ::= { hwDevSystemTrapsPrefix 8 }


        -- 1.3.6.1.4.1.2011.6.3.8.3.2
        hwDevFrameTraps OBJECT IDENTIFIER ::= { hwDevAlarmTraps 2 }

        -- 1.3.6.1.4.1.2011.6.3.8.3.2.0
        hwDevFrameTrapsPrefix OBJECT IDENTIFIER ::= { hwDevFrameTraps 0 }

        -- 1.3.6.1.4.1.2011.6.3.8.3.2.0.1
        hwDevFrameTypeInconsistentTrap NOTIFICATION-TYPE
            OBJECTS { hwFrameIndex, hwFrameType, hwFrameTypeConfigured }
            STATUS current
            DESCRIPTION
                "
                This trap message is reported when the actual shelf type is inconsistent
                with the configuration in the database of device. In this case,
                the configuration data delivery fails.
                "
            ::= { hwDevFrameTrapsPrefix 1 }


        -- 1.3.6.1.4.1.2011.6.3.8.3.2.0.2
        hwDevFrameRestoreTrap NOTIFICATION-TYPE
            OBJECTS { hwFrameIndex, hwFrameTypeName, hwExtendBoardFrameIndex, hwExtendBoardSlotIndex, hwExtendBoardPortIndex
                 }
            STATUS current
            DESCRIPTION
                "
                This trap message is reported when the communication of the frame restored.
                "
            ::= { hwDevFrameTrapsPrefix 2 }


        -- 1.3.6.1.4.1.2011.6.3.8.3.2.0.3
        hwDevFrameFaultTrap NOTIFICATION-TYPE
            OBJECTS { hwFrameIndex, hwFrameTypeName, hwExtendBoardFrameIndex, hwExtendBoardSlotIndex, hwExtendBoardPortIndex
                 }
            STATUS current
            DESCRIPTION
                "
                This trap message is reported when the communication of the frame interrupted,
                the services in the frame fail.
                "
            ::= { hwDevFrameTrapsPrefix 3 }


        -- 1.3.6.1.4.1.2011.6.3.8.3.2.0.4
        hwDevExtendedFrameTypeInconsistentTrap NOTIFICATION-TYPE
            OBJECTS { hwFrameIndex, hwFrameTypeConfigured, hwFrameType, hwExtendBoardFrameIndex, hwExtendBoardSlotIndex,
                hwExtendBoardPortIndex }
            STATUS current
            DESCRIPTION
                "
                This trap message is reported when the actual shelf type is inconsistent
                with the configuration in the database of device. In this case,
                the configuration data delivery fails.
                "
            ::= { hwDevFrameTrapsPrefix 4 }


        -- 1.3.6.1.4.1.2011.6.3.8.3.2.0.5
        hwDevExtendedFrameDyingGaspAlarmTrap NOTIFICATION-TYPE
            OBJECTS { hwFrameIndex, hwFrameTypeName, hwExtendBoardFrameIndex, hwExtendBoardSlotIndex, hwExtendBoardPortIndex
                 }
            STATUS current
            DESCRIPTION
                "
                This trap message is reported when the dying-gasp of
                the extended frame occurs.
                "
            ::= { hwDevFrameTrapsPrefix 5 }

        -- 1.3.6.1.4.1.2011.6.3.8.3.2.0.6
        hwDevExtendedFrameDyingGaspRestoreTrap NOTIFICATION-TYPE
            OBJECTS { hwFrameIndex, hwFrameTypeName, hwExtendBoardFrameIndex, hwExtendBoardSlotIndex, hwExtendBoardPortIndex
                 }
            STATUS current
            DESCRIPTION
                "
                This trap message is reported when the dying-gasp of
                the extended frame recovers.
                "
            ::= { hwDevFrameTrapsPrefix 6 }


        -- 1.3.6.1.4.1.2011.6.3.8.3.2.0.7
        hwDevFrameIdOverLoadTrap NOTIFICATION-TYPE
            OBJECTS { hwFrameTypeName, hwExtendBoardFrameIndex, hwExtendBoardSlotIndex, hwExtendBoardPortIndex }
            STATUS current
            DESCRIPTION
                "
                This trap message is reported when the frame ID exceeded the maximal number.
                "
            ::= { hwDevFrameTrapsPrefix 7 }


        -- 1.3.6.1.4.1.2011.6.3.8.3.2.0.8
        hwDevFrameCmtsAntitheftAuthFailTrap NOTIFICATION-TYPE
            OBJECTS { hwFrameIndex, hwFrameTypeName, hwExtendBoardFrameIndex, hwExtendBoardSlotIndex, hwExtendBoardPortIndex
                 }
            STATUS current
            DESCRIPTION
                "
                This trap message is reported when the anti-theft authentication of the extended frame fails.
                "
            ::= { hwDevFrameTrapsPrefix 8 }

        -- 1.3.6.1.4.1.2011.6.3.8.3.2.0.9
        hwDevFrameCmtsAntitheftAuthRestoreTrap NOTIFICATION-TYPE
            OBJECTS { hwFrameIndex, hwFrameTypeName, hwExtendBoardFrameIndex, hwExtendBoardSlotIndex, hwExtendBoardPortIndex
                 }
            STATUS current
            DESCRIPTION
                "
                This trap message is reported when the anti-theft authentication of the extended frame succeeds.
                "
            ::= { hwDevFrameTrapsPrefix 9 }



        -- 1.3.6.1.4.1.2011.6.3.8.3.2.0.10
        hwVccDataLinkFault NOTIFICATION-TYPE
            OBJECTS { hwVccLocalChassisId, hwVccNeighbourChassisId, hwVccGroupId, hwVccLinkIfPhysicIndex, hwVccLinkIfPhysicName }
	    STATUS current
	    DESCRIPTION 
		"
		This trap message is reported when the data link changes to down.
		"
	    ::= { hwDevFrameTrapsPrefix 10 }


        -- 1.3.6.1.4.1.2011.6.3.8.3.2.0.11
        hwVccDataLinkFaultResume NOTIFICATION-TYPE
            OBJECTS { hwVccLocalChassisId, hwVccNeighbourChassisId, hwVccGroupId, hwVccLinkIfPhysicIndex, hwVccLinkIfPhysicName }
	    STATUS current
	    DESCRIPTION 
		"
		This trap message is reported when the data link changes to up.
		"
	    ::= { hwDevFrameTrapsPrefix 11 }


        -- 1.3.6.1.4.1.2011.6.3.8.3.2.0.12
        hwVccDataChannelFault NOTIFICATION-TYPE
            OBJECTS { hwVccLocalChassisId, hwVccNeighbourChassisId, hwVccGroupId }
	    STATUS current
	    DESCRIPTION 
		"
		This trap message is reported when the data channel changes to down.
		"
	    ::= { hwDevFrameTrapsPrefix 12 }


        -- 1.3.6.1.4.1.2011.6.3.8.3.2.0.13
        hwVccDataChannelFaultResume NOTIFICATION-TYPE
            OBJECTS { hwVccLocalChassisId, hwVccNeighbourChassisId, hwVccGroupId }
	    STATUS current
	    DESCRIPTION 
		"
		This trap message is reported when the data channel changes to up.
		"
	    ::= { hwDevFrameTrapsPrefix 13 }

        -- 1.3.6.1.4.1.2011.6.3.8.3.2.0.14
        hwDeviceHighTemperatureMinorFaultTrap NOTIFICATION-TYPE
            OBJECTS { hwFrameIndex, hwDeviceCurrentTemp, hwDevTempMinorAlmThreshold }
	    STATUS current
	    DESCRIPTION 
		"
		This trap message is reported when the device temperature exceeds the level-1 high temperature alarm threshold.
		"
	    ::= { hwDevFrameTrapsPrefix 14 }

        -- 1.3.6.1.4.1.2011.6.3.8.3.2.0.15
        hwDeviceHighTemperatureMinorRestoreTrap NOTIFICATION-TYPE
            OBJECTS { hwFrameIndex, hwDeviceCurrentTemp, hwDevTempMinorAlmThreshold }
	    STATUS current
	    DESCRIPTION 
		"
		This trap message is reported when the device temperature exceeds the threshold for level-1 high temperature alarm recovery.
		"
	    ::= { hwDevFrameTrapsPrefix 15 } 
	    
-- 1.3.6.1.4.1.2011.6.3.8.3.2.0.16
        hwDeviceHighTemperatureMajorFaultTrap NOTIFICATION-TYPE
            OBJECTS { hwFrameIndex, hwDeviceCurrentTemp, hwDevTempMajorAlmThreshold }
	    STATUS current
	    DESCRIPTION 
		"
		This trap message is reported when the device temperature exceeds the level-2 high temperature alarm threshold.
		"
	    ::= { hwDevFrameTrapsPrefix 16 }
        
        -- 1.3.6.1.4.1.2011.6.3.8.3.2.0.17
        hwDeviceHighTemperatureMajorRestoreTrap NOTIFICATION-TYPE
            OBJECTS { hwFrameIndex, hwDeviceCurrentTemp, hwDevTempMajorAlmThreshold }
	    STATUS current
	    DESCRIPTION 
		"
		This trap message is reported when the device temperature exceeds the threshold for level-2 high temperature alarm recovery.
		"
	    ::= { hwDevFrameTrapsPrefix 17 } 

        -- 1.3.6.1.4.1.2011.6.3.8.3.2.0.18
        hwDeviceHighTemperatureCriticalFaultTrap NOTIFICATION-TYPE
            OBJECTS { hwFrameIndex, hwDeviceCurrentTemp, hwDevTempCriticalAlmThreshold }
	    STATUS current
	    DESCRIPTION 
		"
		This trap message is reported when the device temperature exceeds the level-3 high temperature alarm threshold.
		"
	    ::= { hwDevFrameTrapsPrefix 18 }
        
        -- 1.3.6.1.4.1.2011.6.3.8.3.2.0.19
        hwDeviceHighTemperatureCriticalRestoreTrap NOTIFICATION-TYPE
            OBJECTS { hwFrameIndex, hwDeviceCurrentTemp, hwDevTempCriticalAlmThreshold }
	    STATUS current
	    DESCRIPTION 
		"
		This trap message is reported when the device temperature exceeds the threshold for level-3 high temperature alarm recovery.
		"
	    ::= { hwDevFrameTrapsPrefix 19 } 

        -- 1.3.6.1.4.1.2011.6.3.8.3.3
        hwDevBoardTraps OBJECT IDENTIFIER ::= { hwDevAlarmTraps 3 }

        -- 1.3.6.1.4.1.2011.6.3.8.3.3.0
        hwDevBoardTrapsPrefix OBJECT IDENTIFIER ::= { hwDevBoardTraps 0 }


        -- 1.3.6.1.4.1.2011.6.3.8.3.3.0.1
        hwDevBoardMisMatchTrap NOTIFICATION-TYPE
            OBJECTS { hwFrameIndex, hwSlotIndex, hwSlotTypeName, hwActualSlotTypeName }
            STATUS current
            DESCRIPTION
                "
                This trap message is reported when the type of the board that the user configured is inconsistent
                with the type of the board that is actually inserted.
                "
            ::= { hwDevBoardTrapsPrefix 1 }

        -- 1.3.6.1.4.1.2011.6.3.8.3.3.0.3
        hwDevBoardFaultTrap NOTIFICATION-TYPE
            OBJECTS { hwFrameIndex, hwSlotIndex, hwSlotTypeName }
            STATUS current
            DESCRIPTION
                "
                This trap message is reported when the communication of the board interrupted,
                the services in the board fail.
                "
            ::= { hwDevBoardTrapsPrefix 3 }


        -- 1.3.6.1.4.1.2011.6.3.8.3.3.0.4
        hwDevBoardRestoreTrap NOTIFICATION-TYPE
            OBJECTS { hwFrameIndex, hwSlotIndex, hwSlotTypeName }
            STATUS current
            DESCRIPTION
                "
                This trap message is reported when the communication of the board restored.
                "
            ::= { hwDevBoardTrapsPrefix 4 }

        -- 1.3.6.1.4.1.2011.6.3.8.3.3.0.5
        hwDevBoardReplacedTrap NOTIFICATION-TYPE
            OBJECTS { hwFrameIndex, hwSlotIndex, hwDevPreSlotTypeName, hwSlotTypeName, hwDevPreSlotPhySerialNum,
                hwSlotPhySerialNum }
            STATUS current
            DESCRIPTION
                "
                This trap message is reported when the board is successfully replaced by another board of the same type.
                "
            ::= { hwDevBoardTrapsPrefix 5 }


        -- 1.3.6.1.4.1.2011.6.3.8.3.3.0.6
        hwDevBoardEnterTemperatureProctectModeTrap NOTIFICATION-TYPE
            OBJECTS { hwFrameIndex, hwSlotIndex, hwSlotTemprature }
            STATUS current
            DESCRIPTION
                "
                This trap message is reported when the temperature of active control board is too high,
                all the LAN switch ports of the service board will be powered off  except GIU board.
                "
            ::= { hwDevBoardTrapsPrefix 6 }

        -- 1.3.6.1.4.1.2011.6.3.8.3.3.0.7
        hwDevBoardExitTemperatureProctectModeTrap NOTIFICATION-TYPE
            OBJECTS { hwFrameIndex, hwSlotIndex, hwSlotTemprature }
            STATUS current
            DESCRIPTION
                "
                This trap message is reported when the temperature of active control board
                recovers to safe region from high temperature risk region,
                all the LAN switch ports of the service board will be powered on.
                "
            ::= { hwDevBoardTrapsPrefix 7 }

        -- 1.3.6.1.4.1.2011.6.3.8.3.3.0.8
        hwDevBoardTemperatureTooHighTrap NOTIFICATION-TYPE
            OBJECTS { hwFrameIndex, hwSlotIndex, hwSlotTemprature }
            STATUS current
            DESCRIPTION
                "
                This trap message is reported when the current temperature of service board
                exceed the high temperature threshold.
                "
            ::= { hwDevBoardTrapsPrefix 8 }


        -- 1.3.6.1.4.1.2011.6.3.8.3.3.0.9
        hwDevBoardTemperatureTooHighRecoverTrap NOTIFICATION-TYPE
            OBJECTS { hwFrameIndex, hwSlotIndex, hwSlotTemprature }
            STATUS current
            DESCRIPTION
                "
                This trap message is reported when the current temperature of service board
                recovers to the normal range from high temperature.
                "
            ::= { hwDevBoardTrapsPrefix 9 }


        -- 1.3.6.1.4.1.2011.6.3.8.3.3.0.10
        hwDevBoardTemperatureTooLowTrap NOTIFICATION-TYPE
            OBJECTS { hwFrameIndex, hwSlotIndex, hwSlotTemprature }
            STATUS current
            DESCRIPTION
                "
                This trap message is reported when the current temperature of service board
                is exceed the low temperature threshold.
                "
            ::= { hwDevBoardTrapsPrefix 10 }

        -- 1.3.6.1.4.1.2011.6.3.8.3.3.0.11
        hwDevBoardTemperatureTooLowRecoverTrap NOTIFICATION-TYPE
            OBJECTS { hwFrameIndex, hwSlotIndex, hwSlotTemprature }
            STATUS current
            DESCRIPTION
                "
                This trap message is reported when the current temperature of service board
                recovers to normal range from low temperature.
                "
            ::= { hwDevBoardTrapsPrefix 11 }


        -- 1.3.6.1.4.1.2011.6.3.8.3.3.0.12
        hwDevPowerInputFaultTrap NOTIFICATION-TYPE
            OBJECTS { hwFrameIndex, hwSlotIndex }
            STATUS current
            DESCRIPTION
                "
                This trap message is reported when the power input of the local shelf fails.
                "
            ::= { hwDevBoardTrapsPrefix 12 }

        -- 1.3.6.1.4.1.2011.6.3.8.3.3.0.13
        hwDevPowerInputRecoverTrap NOTIFICATION-TYPE
            OBJECTS { hwFrameIndex, hwSlotIndex }
            STATUS current
            DESCRIPTION
                "
                This trap message is reported when the power input of the local shelf Recovers.
                "
            ::= { hwDevBoardTrapsPrefix 13 }

        -- 1.3.6.1.4.1.2011.6.3.8.3.3.0.14
        hwDevBoardOnlineStateTrap NOTIFICATION-TYPE
            OBJECTS { hwFrameIndex, hwSlotIndex, hwSlotType, hwSlotOperStatus }
            STATUS current
            DESCRIPTION
                "
                This trap message is reported when the state of the board is online.
                "
            ::= { hwDevBoardTrapsPrefix 14 }


        -- 1.3.6.1.4.1.2011.6.3.8.3.3.0.16
        hwDevBoardPower5VFaultTrap NOTIFICATION-TYPE
            OBJECTS { hwFrameIndex, hwSlotIndex, hwSlotTypeName }
            STATUS current
            DESCRIPTION
                "
                This trap message is reported when the inner power of the board is abnormal.
                "
            ::= { hwDevBoardTrapsPrefix 16 }

        -- 1.3.6.1.4.1.2011.6.3.8.3.3.0.17
        hwDevBoardPower5VResumeTrap NOTIFICATION-TYPE
            OBJECTS { hwFrameIndex, hwSlotIndex, hwSlotTypeName }
            STATUS current
            DESCRIPTION
                "
                This trap message is reported when the inner power of the board resumes.
                "
            ::= { hwDevBoardTrapsPrefix 17 }


        -- 1.3.6.1.4.1.2011.6.3.8.3.3.0.18
        hwDevStorageFaultTrap NOTIFICATION-TYPE
            OBJECTS { hwFrameIndex, hwSlotIndex, hwTrapStorageName }
            STATUS current
            DESCRIPTION
                "
                This trap message is reported when the certain storage is hardware fault or
                software fault.
                "
            ::= { hwDevBoardTrapsPrefix 18 }

        -- 1.3.6.1.4.1.2011.6.3.8.3.3.0.21
        hwDevStorageFaultRestoreTrap NOTIFICATION-TYPE
            OBJECTS { hwFrameIndex, hwSlotIndex, hwTrapStorageName }
            STATUS current
            DESCRIPTION
                "
                This trap message is reported when the certain storage is hardware fault or
                software fault recovers.
                "
            ::= { hwDevBoardTrapsPrefix 21 }


        -- 1.3.6.1.4.1.2011.6.3.8.3.3.0.22
        hwFtpConfigureTrap NOTIFICATION-TYPE
            OBJECTS { hwSysVersion }
            STATUS current
            DESCRIPTION
                "
                This trap message is reported when the board need automatic expand.
                "
            ::= { hwDevBoardTrapsPrefix 22 }

        -- 1.3.6.1.4.1.2011.6.3.8.3.3.0.23
        hwDevBoardAutomaticExpandFailTrap NOTIFICATION-TYPE
            OBJECTS { hwFrameIndex, hwSlotIndex }
            STATUS current
            DESCRIPTION
                "
                This trap message is reported when the board automatic expand fail.
                "
            ::= { hwDevBoardTrapsPrefix 23 }


        -- 1.3.6.1.4.1.2011.6.3.8.3.3.0.24
        hwDevBoardAutomaticExpandRestoreTrap NOTIFICATION-TYPE
            OBJECTS { hwFrameIndex, hwSlotIndex }
            STATUS current
            DESCRIPTION
                "
                This trap message is reported when the board automatic expand fail recovers.
                "
            ::= { hwDevBoardTrapsPrefix 24 }

        -- 1.3.6.1.4.1.2011.6.3.8.3.3.0.26
        hwDevBoardInputFaultTrap NOTIFICATION-TYPE
            OBJECTS { hwFrameIndex, hwSlotIndex, hwSlotInputIdIndex, hwSlotInputType }
            STATUS current
            DESCRIPTION
                "
                This trap message is reported when the input voltage of a line cannot be detected.
                "
            ::= { hwDevBoardTrapsPrefix 26 }

        -- 1.3.6.1.4.1.2011.6.3.8.3.3.0.27
        hwDevBoardInputRecoverTrap NOTIFICATION-TYPE
            OBJECTS { hwFrameIndex, hwSlotIndex, hwSlotInputIdIndex, hwSlotInputType }
            STATUS current
            DESCRIPTION
                "
                This trap message is reported when detected power unit singals recover.
                "
            ::= { hwDevBoardTrapsPrefix 27 }

        -- 1.3.6.1.4.1.2011.6.3.8.3.3.0.28
        hwDevPowerLackVoltageFaultTrap NOTIFICATION-TYPE
            OBJECTS { hwFrameIndex }
            STATUS current
            DESCRIPTION
                "
                This trap message is reported when remote power supply input is under-voltage.
                "
            ::= { hwDevBoardTrapsPrefix 28 }


        -- 1.3.6.1.4.1.2011.6.3.8.3.3.0.29
        hwDevPowerLackVolitageRecoverTrap NOTIFICATION-TYPE
            OBJECTS { hwFrameIndex }
            STATUS current
            DESCRIPTION
                "
                This trap message is reported when voltage in the subrack recovers.
                "
            ::= { hwDevBoardTrapsPrefix 29 }
            
        -- 1.3.6.1.4.1.2011.6.3.8.3.3.0.30
        hwDevBoardReplaceFailTrap NOTIFICATION-TYPE
            OBJECTS { hwFrameIndex, hwSlotIndex, hwSlotTypeName, hwActualSlotTypeName }
            STATUS current
            DESCRIPTION
                "
                This trap message is reported when the original board failed to replace with a new board.
                "
            ::= { hwDevBoardTrapsPrefix 30 }
      
        -- 1.3.6.1.4.1.2011.6.3.8.3.3.0.31
        hwDevPowerPortInputFaultTrap NOTIFICATION-TYPE
            OBJECTS { hwFrameIndex, hwSlotIndex, hwTrapPowerPortIndex }
            STATUS current
            DESCRIPTION
                "
                This trap message is reported when the power input of the local shelf fails.
                "
            ::= { hwDevBoardTrapsPrefix 31 }

        -- 1.3.6.1.4.1.2011.6.3.8.3.3.0.32
        hwDevPowerPortInputRecoverTrap NOTIFICATION-TYPE
            OBJECTS { hwFrameIndex, hwSlotIndex, hwTrapPowerPortIndex }
            STATUS current
            DESCRIPTION
                "
                This trap message is reported when the power input of the local shelf Recovers.
                "
            ::= { hwDevBoardTrapsPrefix 32 }
            
        -- 1.3.6.1.4.1.2011.6.3.8.3.4
        hwDevSubBoardTraps OBJECT IDENTIFIER ::= { hwDevAlarmTraps 4 }


        -- 1.3.6.1.4.1.2011.6.3.8.3.4.0
        hwDevSubBoardTrapsPrefix OBJECT IDENTIFIER ::= { hwDevSubBoardTraps 0 }

        -- 1.3.6.1.4.1.2011.6.3.8.3.4.0.1
        hwDevSubBoardTypeInconsistentTrap NOTIFICATION-TYPE
            OBJECTS { hwFrameIndex, hwSlotIndex }
            STATUS current
            DESCRIPTION
                "
                This trap message is reported when the configured daughter board type
                or quantity is not the same as the actual type or quantity.
                "
            ::= { hwDevSubBoardTrapsPrefix 1 }

        -- 1.3.6.1.4.1.2011.6.3.8.3.4.0.2
        hwDevSubBoardMisMatchTrap NOTIFICATION-TYPE
            OBJECTS { hwFrameIndex, hwSlotIndex, hwSubslotTypeName, hwSubslotTypeName }
            STATUS current
            DESCRIPTION
                "
                This trap message is reported when the combination of daughter board type
                in main control board is not supported.
                "
            ::= { hwDevSubBoardTrapsPrefix 2 }


        -- 1.3.6.1.4.1.2011.6.3.8.3.4.0.3
        hwDevSubBoardReplacedTrap NOTIFICATION-TYPE
            OBJECTS { hwFrameIndex, hwSlotIndex, hwOldSubslotType0, hwSubslotType, hwOldSubslotType1,
                hwSubslotType, hwOldSubslotType2, hwSubslotType, hwOldSubslotType3, hwSubslotType
                 }
            STATUS current
            DESCRIPTION
                "
                This trap message is reported when the board is successfully
                replaced by another board of the same type.
                "
            ::= { hwDevSubBoardTrapsPrefix 3 }

        -- 1.3.6.1.4.1.2011.6.3.8.3.4.0.4
        hwDevSubBoardTemperatureTooHighTrap NOTIFICATION-TYPE
            OBJECTS { hwFrameIndex, hwSlotIndex, hwSubboardID, hwSlotTemprature }
            STATUS current
            DESCRIPTION
                "
                This trap message is reported when the current temperature of service sub board
                exceed the high temperature threshold.
                "
            ::= { hwDevSubBoardTrapsPrefix 4 }

        -- 1.3.6.1.4.1.2011.6.3.8.3.4.0.5
        hwDevSubBoardTemperatureTooHighRecoverTrap NOTIFICATION-TYPE
            OBJECTS { hwFrameIndex, hwSlotIndex, hwSubboardID, hwSlotTemprature }
            STATUS current
            DESCRIPTION
                "
                This trap message is reported when the current temperature of service sub board
                recovers to the normal range from high temperature.
                "
            ::= { hwDevSubBoardTrapsPrefix 5 }	

        -- 1.3.6.1.4.1.2011.6.3.8.3.4.0.6
        hwDevSubBoardFaultTrap NOTIFICATION-TYPE
            OBJECTS { hwFrameIndex, hwSlotIndex, hwSubboardID }
            STATUS current
            DESCRIPTION
                "
                This trap message is reported when the communication of the board interrupted.
                "
            ::= { hwDevSubBoardTrapsPrefix 6 }

        -- 1.3.6.1.4.1.2011.6.3.8.3.4.0.7
        hwDevSubBoardFaultRecoverTrap NOTIFICATION-TYPE
            OBJECTS { hwFrameIndex, hwSlotIndex, hwSubboardID }
            STATUS current
            DESCRIPTION
                "
                This trap message is reported when the communication of the board restored.
                "
            ::= { hwDevSubBoardTrapsPrefix 7 }	
			
			
        -- 1.3.6.1.4.1.2011.6.3.8.3.5
        hwDevDiagTraps OBJECT IDENTIFIER ::= { hwDevAlarmTraps 5 }


        -- 1.3.6.1.4.1.2011.6.3.8.3.5.0
        hwDevDiagTrapsPrefix OBJECT IDENTIFIER ::= { hwDevDiagTraps 0 }


        -- 1.3.6.1.4.1.2011.6.3.8.3.5.0.1
        hwDiagResOverloadFaultTrap NOTIFICATION-TYPE
            OBJECTS { hwResType, hwResOccupancy }
            STATUS current
            DESCRIPTION
                "
                This trap message is reported when the system resources usage exceeds the threshold
                The system resources include system CPU, system memory, and system messages.
                "
            ::= { hwDevDiagTrapsPrefix 1 }


        -- 1.3.6.1.4.1.2011.6.3.8.3.5.0.2
        hwDiagResOverloadRestoreTrap NOTIFICATION-TYPE
            OBJECTS { hwResType, hwResOccupancy }
            STATUS current
            DESCRIPTION
                "
                This trap message is reported when the system resources usage recovers
                from the overload state to the normal state.
                "
            ::= { hwDevDiagTrapsPrefix 2 }
--  hwDevGeneralTraps OBJECT IDENTIFIER ::= { hwDevTraps 5 0 }
-- VRPV8R1 Capability 20100828 modify

        -- 1.3.6.1.4.1.2011.6.3.8.5
        hwDevGeneralTrapsPre OBJECT IDENTIFIER ::= { hwDevTraps 5 }



        -- 1.3.6.1.4.1.2011.6.3.8.5.0
        hwDevGeneralTraps OBJECT IDENTIFIER ::= { hwDevGeneralTrapsPre 0 }


        -- 1.3.6.1.4.1.2011.6.3.8.5.0.1
        hwFrameAdminResultTrap NOTIFICATION-TYPE
            OBJECTS { hwFrameIndex, hwFrameAdminStatus, hwFrameAdminResult }
            STATUS current
            DESCRIPTION
                "
                Frame administration result Trap report
                "
            ::= { hwDevGeneralTraps 1 }


        -- 1.3.6.1.4.1.2011.6.3.8.5.0.2
        hwSlotAdminResultTrap NOTIFICATION-TYPE
            OBJECTS { hwFrameIndex, hwSlotIndex, hwSlotAdminStatus, hwSlotAdminResult }
            STATUS current
            DESCRIPTION
                "
                Slot administration result Trap report
                "
            ::= { hwDevGeneralTraps 2 }


        -- 1.3.6.1.4.1.2011.6.3.8.5.0.3
        hwSubSlotAdminResultTrap NOTIFICATION-TYPE
            OBJECTS { hwFrameIndex, hwSlotIndex, hwSubslotIndex, hwSubslotAdminStatus, hwSubslotAdminResult
                 }
            STATUS current
            DESCRIPTION
                "
                Subslot administration result Trap report
                "
            ::= { hwDevGeneralTraps 3 }


        -- 1.3.6.1.4.1.2011.6.3.8.5.0.4
        hwPortAdminResultTrap NOTIFICATION-TYPE
            OBJECTS { hwFrameIndex, hwSlotIndex, hwSubslotIndex, hwPortIndex, hwPortAdminStatus,
                hwPortAdminResult }
            STATUS current
            DESCRIPTION
                "
                Port administration result Trap report
                "
            ::= { hwDevGeneralTraps 4 }

        -- 1.3.6.1.4.1.2011.6.3.9
        hwAppBoardPara OBJECT IDENTIFIER ::= { hwDev 9 }

        -- 1.3.6.1.4.1.2011.6.3.9.1
        hwAppBoardGlobalPara OBJECT IDENTIFIER ::= { hwAppBoardPara 1 }


        -- 1.3.6.1.4.1.2011.6.3.9.1.1
        hwAppBoardPhySlot OBJECT-TYPE
            SYNTAX Integer32
            MAX-ACCESS read-only
            STATUS current
            DESCRIPTION
                "
                The location of Application board.
                                "
            ::= { hwAppBoardGlobalPara 1 }

        -- 1.3.6.1.4.1.2011.6.3.9.2
        hwAppBoardMngtTable OBJECT-TYPE
            SYNTAX SEQUENCE OF HwAppBoardMngtEntry
            MAX-ACCESS not-accessible
            STATUS current
            DESCRIPTION
                "
                The index of this table is hwFrameIndex or hwSlotIndex.
                This is the App Application IP configuration table.
                This table is used to configure and query the IP configuration mode and IP address of an Application board.
                "
            ::= { hwAppBoardPara 2 }


        -- 1.3.6.1.4.1.2011.6.3.9.2.1
        hwAppBoardMngtEntry OBJECT-TYPE
            SYNTAX HwAppBoardMngtEntry
            MAX-ACCESS not-accessible
            STATUS current
            DESCRIPTION
                "
                The index of this entry is hwFrameIndex or hwSlotIndex.
                This is the App Application IP configuration table.
                This table is used to configure and query the IP configuration mode and IP address of an Application board.
                "
            INDEX { hwFrameIndex, hwSlotIndex }
            ::= { hwAppBoardMngtTable 1 }


        HwAppBoardMngtEntry ::=
            SEQUENCE {
                hwAppBoardMngtVlan
                    Integer32,
                hwAppBoardMngtIpType
                    InetAddressType,
                hwAppBoardMngtIp
                    InetAddress,
                hwAppBoardMngtMaskLength
                    Integer32,
                hwAppBoardMngtGateway
                    InetAddress,
                hwAppBoardMngtRowStatus
                    RowStatus
             }

        -- 1.3.6.1.4.1.2011.6.3.9.2.1.1
        hwAppBoardMngtVlan OBJECT-TYPE
            SYNTAX Integer32 (1..4093)
            MAX-ACCESS read-write
            STATUS current
            DESCRIPTION
                "
                The management VLAN of Application board.
                Range: 1-4093
                "
            ::= { hwAppBoardMngtEntry 1 }


        -- 1.3.6.1.4.1.2011.6.3.9.2.1.2
        hwAppBoardMngtIpType OBJECT-TYPE
            SYNTAX InetAddressType
            MAX-ACCESS read-write
            STATUS current
            DESCRIPTION
                "
                The type of Ip address.
                IPV4:1
                IPV6:2
                "
            ::= { hwAppBoardMngtEntry 2 }


        -- 1.3.6.1.4.1.2011.6.3.9.2.1.3
        hwAppBoardMngtIp OBJECT-TYPE
            SYNTAX InetAddress
            MAX-ACCESS read-write
            STATUS current
            DESCRIPTION
                "
                The IP address of the Application board
                "
            ::= { hwAppBoardMngtEntry 3 }


        -- 1.3.6.1.4.1.2011.6.3.9.2.1.4
        hwAppBoardMngtMaskLength OBJECT-TYPE
            SYNTAX Integer32 (0..128)
            MAX-ACCESS read-write
            STATUS current
            DESCRIPTION
                "
                The mask length of the ip address.
                Range: 0-128
                "
            ::= { hwAppBoardMngtEntry 4 }


        -- 1.3.6.1.4.1.2011.6.3.9.2.1.5
        hwAppBoardMngtGateway OBJECT-TYPE
            SYNTAX InetAddress
            MAX-ACCESS read-write
            STATUS current
            DESCRIPTION
                "
                The gateway of the Application board
                "
            ::= { hwAppBoardMngtEntry 5 }


        -- 1.3.6.1.4.1.2011.6.3.9.2.1.6
        hwAppBoardMngtRowStatus OBJECT-TYPE
            SYNTAX RowStatus
            MAX-ACCESS read-create
            STATUS current
            DESCRIPTION
                "
                RowStatus standard operation.
                "
            ::= { hwAppBoardMngtEntry 6 }
        -- 1.3.6.1.4.1.2011.6.3.10
        hwCliUserMgmt OBJECT IDENTIFIER ::= { hwDev 10 }


        -- 1.3.6.1.4.1.2011.6.3.10.1
        hwCliUserParaTable OBJECT-TYPE
            SYNTAX SEQUENCE OF HwCliUserParaEntry
            MAX-ACCESS not-accessible
            STATUS current
            DESCRIPTION
                "
                CLI user parameters configuration table.
                "
            ::= { hwCliUserMgmt 1 }

        -- 1.3.6.1.4.1.2011.6.3.10.1.1
        hwCliUserParaEntry OBJECT-TYPE
            SYNTAX HwCliUserParaEntry
            MAX-ACCESS not-accessible
            STATUS current
            DESCRIPTION
                "
                CLI user parameters configuration table entity.
                "
            INDEX { IMPLIED hwCliUserName }
            ::= { hwCliUserParaTable 1 }


        HwCliUserParaEntry ::=
            SEQUENCE {
                hwCliUserName
                    OCTET STRING,
                hwCliUserPassword
                    OCTET STRING,
                hwCliUserLevel
                    INTEGER,
                hwCliUserLogins
                    Integer32,
                hwCliUserDecr
                    OCTET STRING,
                hwCliUserRowStatus
                    RowStatus
             }

        -- 1.3.6.1.4.1.2011.6.3.10.1.1.1
        hwCliUserName OBJECT-TYPE
            SYNTAX OCTET STRING (SIZE (1..15))
            MAX-ACCESS not-accessible
            STATUS current
            DESCRIPTION
                "
                Name of the CLI user.
                "
            ::= { hwCliUserParaEntry 1 }


        -- 1.3.6.1.4.1.2011.6.3.10.1.1.2
        hwCliUserPassword OBJECT-TYPE
            SYNTAX OCTET STRING (SIZE (0..15))
            MAX-ACCESS read-create
            STATUS current
            DESCRIPTION
                "
                password of the CLI user.
                "
            ::= { hwCliUserParaEntry 2 }


        -- 1.3.6.1.4.1.2011.6.3.10.1.1.3
        hwCliUserLevel OBJECT-TYPE
            SYNTAX INTEGER
                {
                common(1),
                operator(2),
                administrator(3)
                }
            MAX-ACCESS read-create
            STATUS current
            DESCRIPTION
                "
                Level of CLI user(1:common,2:operator,3:administrator).
                "
            ::= { hwCliUserParaEntry 3 }

        -- 1.3.6.1.4.1.2011.6.3.10.1.1.4
        hwCliUserLogins OBJECT-TYPE
            SYNTAX Integer32 (0..4)
            MAX-ACCESS read-create
            STATUS current
            DESCRIPTION
                "
                The num of user can login in one time.
                "
            ::= { hwCliUserParaEntry 4 }


        -- 1.3.6.1.4.1.2011.6.3.10.1.1.5
        hwCliUserDecr OBJECT-TYPE
            SYNTAX OCTET STRING (SIZE (0..30))
            MAX-ACCESS read-create
            STATUS current
            DESCRIPTION
                "
                Description of CLI user.
                "
            ::= { hwCliUserParaEntry 5 }


        -- 1.3.6.1.4.1.2011.6.3.10.1.1.6
        hwCliUserRowStatus OBJECT-TYPE
            SYNTAX RowStatus
            MAX-ACCESS read-create
            STATUS current
            DESCRIPTION
                "
                Operation status of CLI user,the CLI user
                can be added,deleted and modified.
                "
            ::= { hwCliUserParaEntry 6 }


        -- 1.3.6.1.4.1.2011.6.3.10.2
        hwCliClientTable OBJECT-TYPE
            SYNTAX SEQUENCE OF HwCliClientEntry
            MAX-ACCESS not-accessible
            STATUS current
            DESCRIPTION
                "
                CLI client table.
                "
            ::= { hwCliUserMgmt 2 }

        -- 1.3.6.1.4.1.2011.6.3.10.2.1
        hwCliClientEntry OBJECT-TYPE
            SYNTAX HwCliClientEntry
            MAX-ACCESS not-accessible
            STATUS current
            DESCRIPTION
                "
                CLI user parameters configuration table entity.
                "
            INDEX { hwCliClientID }
            ::= { hwCliClientTable 1 }


        HwCliClientEntry ::=
            SEQUENCE {
                hwCliClientID
                    Integer32,
                hwCliClientUserName
                    OCTET STRING,
                hwCliClientType
                    INTEGER,
                hwCliClientIp
                    IpAddress,
                hwCliClientLoginTime
                    DateAndTime,
                hwCliClientAdminStatus
                    INTEGER
             }

        -- 1.3.6.1.4.1.2011.6.3.10.2.1.1
        hwCliClientID OBJECT-TYPE
            SYNTAX Integer32 (1..5)
            MAX-ACCESS not-accessible
            STATUS current
            DESCRIPTION
                "
                Client ID(1..5).
                "
            ::= { hwCliClientEntry 1 }


        -- 1.3.6.1.4.1.2011.6.3.10.2.1.2
        hwCliClientUserName OBJECT-TYPE
            SYNTAX OCTET STRING (SIZE (1..15))
            MAX-ACCESS read-only
            STATUS current
            DESCRIPTION
                "
                User name of client.
                "
            ::= { hwCliClientEntry 2 }


        -- 1.3.6.1.4.1.2011.6.3.10.2.1.3
        hwCliClientType OBJECT-TYPE
            SYNTAX INTEGER
                {
                serial(1),
                telnet(2)
                }
            MAX-ACCESS read-only
            STATUS current
            DESCRIPTION
                "
                Type of client(1:serial,2:telnet).
                "
            ::= { hwCliClientEntry 3 }


        -- 1.3.6.1.4.1.2011.6.3.10.2.1.4
        hwCliClientIp OBJECT-TYPE
            SYNTAX IpAddress
            MAX-ACCESS read-only
            STATUS current
            DESCRIPTION
                "
                The IP address of client.
                "
            ::= { hwCliClientEntry 4 }

        -- 1.3.6.1.4.1.2011.6.3.10.2.1.5
        hwCliClientLoginTime OBJECT-TYPE
            SYNTAX DateAndTime
            MAX-ACCESS read-only
            STATUS current
            DESCRIPTION
                "
                Login time of Client.
                "
            ::= { hwCliClientEntry 5 }


        -- 1.3.6.1.4.1.2011.6.3.10.2.1.6
        hwCliClientAdminStatus OBJECT-TYPE
            SYNTAX INTEGER { disconnect(1) }
            MAX-ACCESS read-write
            STATUS current
            DESCRIPTION
                "
                admin status of client, can disconnect client.
                "
            ::= { hwCliClientEntry 6 }



        -- 1.3.6.1.4.1.2011.6.3.11
        hwDevCompatibleTable OBJECT IDENTIFIER ::= { hwDev 11 }


        -- 1.3.6.1.4.1.2011.6.3.11.1
        hwCompatibleSysOid OBJECT-TYPE
            SYNTAX OBJECT IDENTIFIER
            MAX-ACCESS read-only
            STATUS current
            DESCRIPTION
                "
                The compatible SYSOID of new network element.
                "
            ::= { hwDevCompatibleTable 1 }


        -- 1.3.6.1.4.1.2011.6.3.11.2
        hwCompatibleVersion OBJECT-TYPE
            SYNTAX OCTET STRING (SIZE (0..255))
            MAX-ACCESS read-only
            STATUS current
            DESCRIPTION
                "
                The compatible version of new network element.
                "
            ::= { hwDevCompatibleTable 2 }


        -- 1.3.6.1.4.1.2011.6.3.11.3
        hwCompatibleVRCB OBJECT-TYPE
            SYNTAX OCTET STRING (SIZE (0..255))
            MAX-ACCESS read-only
            STATUS current
            DESCRIPTION
                "
                The compatible VRCB of new network element.
                "
            ::= { hwDevCompatibleTable 3 }


        -- 1.3.6.1.4.1.2011.6.3.11.4
        hwCompatibleProductName OBJECT-TYPE
            SYNTAX OCTET STRING (SIZE (0..255))
            MAX-ACCESS read-only
            STATUS current
            DESCRIPTION
                "
                The compatible product name of new network element.
                "
            ::= { hwDevCompatibleTable 4 }


        -- 1.3.6.1.4.1.2011.6.3.101
        hwDevConformance OBJECT IDENTIFIER ::= { hwDev 101 }

        -- 1.3.6.1.4.1.2011.6.3.101.1
        hwDevCompliances OBJECT IDENTIFIER ::= { hwDevConformance 1 }


--   compliance statements
-- this module
-- this module
        -- 1.3.6.1.4.1.2011.6.3.101.1.1
        hwDevCompliance MODULE-COMPLIANCE
            STATUS current
            DESCRIPTION
                "The compliance statement for SNMP entities which implement
                HUAWEI DEVICE MIB."
            MODULE -- this module
                MANDATORY-GROUPS { hwDevCompatibleTableGroup, hwDevCpuGroup, hwDevMemGroup, hwDevBufGroup }
            ::= { hwDevCompliances 1 }


        -- 1.3.6.1.4.1.2011.6.3.101.2
        hwDevGroups OBJECT IDENTIFIER ::= { hwDevConformance 2 }


--   MIB groupings
        -- 1.3.6.1.4.1.2011.6.3.101.2.1
        hwSystemParaGroup OBJECT-GROUP
            OBJECTS { hwSysIpAddr, hwSysIpMask, hwSysTime, hwSysVersion }
            STATUS current
            DESCRIPTION
                "hwSystemPara."
            ::= { hwDevGroups 1 }

        -- 1.3.6.1.4.1.2011.6.3.101.2.2
        hwFrameLinksGroup OBJECT-GROUP
            OBJECTS { hwFrameLinkNextIndex, hwFrameLinkNumber }
            STATUS current
            DESCRIPTION
                "hwFrameLinks."
            ::= { hwDevGroups 2 }


        -- 1.3.6.1.4.1.2011.6.3.101.2.3
        hwDevTrapVbOidsGroup OBJECT-GROUP
            OBJECTS { hwFrameAdminResult, hwSlotAdminResult, hwSubslotAdminResult, hwPortAdminResult }
            STATUS current
            DESCRIPTION
                "hwDevTrapVbOids."
            ::= { hwDevGroups 3 }

        -- 1.3.6.1.4.1.2011.6.3.101.2.4
        hwDevCompatibleTableGroup OBJECT-GROUP
            OBJECTS { hwCompatibleProductName, hwCompatibleSysOid, hwCompatibleVRCB, hwCompatibleVersion }
            STATUS current
            DESCRIPTION
                "hwDevCompatibleTable."
            ::= { hwDevGroups 4 }


        -- 1.3.6.1.4.1.2011.6.3.101.2.5
        hwDevCpuGroup OBJECT-GROUP
            OBJECTS { hwCpuDevDuty, hwAvgDuty1min, hwAvgDuty5min }
            STATUS current
            DESCRIPTION
                "hwDevCpuGroup."
            ::= { hwDevGroups 5 }

        -- 1.3.6.1.4.1.2011.6.3.101.2.6
        hwDevMemGroup OBJECT-GROUP
            OBJECTS { hwMemoryDevSize, hwMemoryDevFree, hwMemoryDevRawSliceUsed, hwMemoryDevLargestFree,
                hwMemoryDevFail, hwMemoryDevFailNoMem, hwMemoryDevSize64, hwMemoryDevFree64 }
            STATUS current
            DESCRIPTION
                "hwDevMemGroup."
            ::= { hwDevGroups 6 }

        -- 1.3.6.1.4.1.2011.6.3.101.2.7
        hwDevBufGroup OBJECT-GROUP
            OBJECTS { hwBufferCurrentTotal, hwBufferCurrentUsed }
            STATUS current
            DESCRIPTION
                "hwDevBufGroup."
            ::= { hwDevGroups 7 }

        -- 1.3.6.1.4.1.2011.6.3.101.2.8
        hwDevGeneralTrapsGroup NOTIFICATION-GROUP
            NOTIFICATIONS { hwSubSlotAdminResultTrap, hwFrameAdminResultTrap, hwPortAdminResultTrap, hwSlotAdminResultTrap }
            STATUS current
            DESCRIPTION
                "hwDevGeneralTraps."
            ::= { hwDevGroups 8 }
        -- 1.3.6.1.4.1.2011.6.3.13
        hwSysRegister OBJECT IDENTIFIER ::= { hwDev 13 }


-- TruthValue
        -- 1.3.6.1.4.1.2011.6.3.13.1
        hwSysHandshakeEnable OBJECT-TYPE
            SYNTAX INTEGER
                {
                nooperation(0),
                true(1),
                false(2)
                }
            MAX-ACCESS read-write
            STATUS current
            DESCRIPTION
                "
                The switch of periodic handshake between the device and the NMS.
                The NMS uses the periodic handshake process to check whether
                the device is properly connected.
                Default: false
                Options:
                1.nooperation(0) -default shakes hands of the system
                2.true(1)        -The device periodically shakes hands with the NMS
                3.false(2)       -The device does not periodically shake hands with the NMS
                "
            ::= { hwSysRegister 1 }


        -- 1.3.6.1.4.1.2011.6.3.13.2
        hwSysHandshakeInterval OBJECT-TYPE
            SYNTAX Unsigned32
            UNITS "Seconds"
            MAX-ACCESS read-write
            STATUS current
            DESCRIPTION
                "
                The interval for sending a handshake packet, in unit of minute
                Note: If the interval for sending a handshake packet is too long,
                the NMS cannot detect the disconnection between the device and the NMS promptly.
                If the interval for sending a handshake packet is too short,
                the number of handshake packets that the NMS needs to handle increases,
                which adds burden to the NMS.
                You can set the time interval according to the actual situation.
                Default: 300
                Unit: Seconds
                "
            ::= { hwSysRegister 2 }


        -- 1.3.6.1.4.1.2011.6.3.13.3
        hwSysRegisterResponseStatus OBJECT-TYPE
            SYNTAX INTEGER
                {
                nooperation(-1),
                registering(1),
                success(2),
                failure(3),
                timeout(4)
                }
            MAX-ACCESS read-write
            STATUS current
            DESCRIPTION
                "
                The NMS response to the periodic handshake packet from the device.
                Options:
                1.nooperation(-1)  -default state of the system
                2.registering(1)   -register is in processing
                3.success(2)       -The registration/handshake packet reported by the device is successfully handled
                4.failure(3)       -register failed
                5.timeout(4)       -register timeout
                "
            ::= { hwSysRegister 3 }


        -- 1.3.6.1.4.1.2011.6.3.15
        hwCustomizedParameter OBJECT IDENTIFIER ::= { hwDev 15 }


        -- 1.3.6.1.4.1.2011.6.3.15.1
        hwCustomizedParameterTable OBJECT-TYPE
            SYNTAX SEQUENCE OF HwCustomizedParameterEntry
            MAX-ACCESS not-accessible
            STATUS current
            DESCRIPTION
                "
                The index of this table is hwParaName.
                Customized parameter table.
                This table is no longer used.
                "
            ::= { hwCustomizedParameter 1 }


        -- 1.3.6.1.4.1.2011.6.3.15.1.1
        hwCustomizedParameterEntry OBJECT-TYPE
            SYNTAX HwCustomizedParameterEntry
            MAX-ACCESS not-accessible
            STATUS current
            DESCRIPTION
                "
                The index of this entry is hwParaName.
                Customized parameter table.
                This table is no longer used.
                "
            INDEX { IMPLIED hwParaName }
            ::= { hwCustomizedParameterTable 1 }


        HwCustomizedParameterEntry ::=
            SEQUENCE {
                hwParaName
                    OCTET STRING,
                hwParaValue
                    OCTET STRING,
                hwParaState
                    INTEGER,
                hwParaRowStatus
                    RowStatus
             }

        -- 1.3.6.1.4.1.2011.6.3.15.1.1.1
        hwParaName OBJECT-TYPE
            SYNTAX OCTET STRING (SIZE (1..32))
            MAX-ACCESS not-accessible
            STATUS current
            DESCRIPTION
                "
                The name of the parameter.
                This object is no longer used.
                "
            ::= { hwCustomizedParameterEntry 1 }


        -- 1.3.6.1.4.1.2011.6.3.15.1.1.2
        hwParaValue OBJECT-TYPE
            SYNTAX OCTET STRING (SIZE (1..64))
            MAX-ACCESS read-create
            STATUS current
            DESCRIPTION
                "
                The value of the parameter.
                This object is no longer used.
                "
            ::= { hwCustomizedParameterEntry 2 }


        -- 1.3.6.1.4.1.2011.6.3.15.1.1.3
        hwParaState OBJECT-TYPE
            SYNTAX INTEGER
                {
                readWrite(1),
                readOnly(2)
                }
            MAX-ACCESS read-create
            STATUS current
            DESCRIPTION
                "
                The overwritten state of the parameter.
                This object is no longer used.
                Options:
                1.readWrite(1) - read and write
                2.readOnly(2)  - read only
                "
            ::= { hwCustomizedParameterEntry 3 }


        -- 1.3.6.1.4.1.2011.6.3.15.1.1.4
        hwParaRowStatus OBJECT-TYPE
            SYNTAX RowStatus
            MAX-ACCESS read-create
            STATUS current
            DESCRIPTION
                "
                RowStatus standard operation.
                This object is no longer used.
                "
            ::= { hwCustomizedParameterEntry 4 }


        -- 1.3.6.1.4.1.2011.6.3.16
        hwAutoReset OBJECT IDENTIFIER ::= { hwDev 16 }


        -- 1.3.6.1.4.1.2011.6.3.16.1
        hwPingAutoResetTable OBJECT-TYPE
            SYNTAX SEQUENCE OF HwPingAutoResetEntry
            MAX-ACCESS not-accessible
            STATUS current
            DESCRIPTION
                "
                The index of this table is hwHostIpAddr.
                Ping auto-reset table.
                "
            ::= { hwAutoReset 1 }


        -- 1.3.6.1.4.1.2011.6.3.16.1.1
        hwPingAutoResetEntry OBJECT-TYPE
            SYNTAX HwPingAutoResetEntry
            MAX-ACCESS not-accessible
            STATUS current
            DESCRIPTION
                "
                The index of this entry is hwHostIpAddr.
                Ping auto-reset table.
                "
            INDEX { hwHostIpAddr }
            ::= { hwPingAutoResetTable 1 }


        HwPingAutoResetEntry ::=
            SEQUENCE {
                hwHostIpAddr
                    IpAddress,
                hwPacketNumber
                    Integer32,
                hwIntervalTime
                    Integer32,
                hwResponseTime
                    Integer32,
                hwLoopTime
                    Integer32,
                hwFailureThreshold
                    Integer32,
                hwFailedTimes
                    Integer32,
                hwAutoResetEnableStatus
                    INTEGER,
                hwAutoResetRowStatus
                    RowStatus
             }

        -- 1.3.6.1.4.1.2011.6.3.16.1.1.1
        hwHostIpAddr OBJECT-TYPE
            SYNTAX IpAddress
            MAX-ACCESS read-only
            STATUS current
            DESCRIPTION
                "
                The IP address of monitoring gateway
                "
            ::= { hwPingAutoResetEntry 1 }


        -- 1.3.6.1.4.1.2011.6.3.16.1.1.2
        hwPacketNumber OBJECT-TYPE
            SYNTAX Integer32
            MAX-ACCESS read-write
            STATUS current
            DESCRIPTION
                "
                The number of the PING packets sent during every check,
                Default value: 5
                "
            ::= { hwPingAutoResetEntry 2 }


        -- 1.3.6.1.4.1.2011.6.3.16.1.1.3
        hwIntervalTime OBJECT-TYPE
            SYNTAX Integer32
            MAX-ACCESS read-write
            STATUS current
            DESCRIPTION
                "
                The interval of sending PING packets.
                Default: 1
                Unit: second
                "
            ::= { hwPingAutoResetEntry 3 }


        -- 1.3.6.1.4.1.2011.6.3.16.1.1.4
        hwResponseTime OBJECT-TYPE
            SYNTAX Integer32
            MAX-ACCESS read-write
            STATUS current
            DESCRIPTION
                "
                Time-out time for the response of the PING packets.
                Unit: second
                Default: 2
                "
            ::= { hwPingAutoResetEntry 4 }


        -- 1.3.6.1.4.1.2011.6.3.16.1.1.5
        hwLoopTime OBJECT-TYPE
            SYNTAX Integer32
            MAX-ACCESS read-write
            STATUS current
            DESCRIPTION
                "
                Interval between the cyclic checks
                Default value: 600
                Unit: second
                "
            ::= { hwPingAutoResetEntry 5 }


        -- 1.3.6.1.4.1.2011.6.3.16.1.1.6
        hwFailureThreshold OBJECT-TYPE
            SYNTAX Integer32
            MAX-ACCESS read-write
            STATUS current
            DESCRIPTION
                "
                The threshold of checking failed.
                Default value: 10
                "
            ::= { hwPingAutoResetEntry 6 }


        -- 1.3.6.1.4.1.2011.6.3.16.1.1.7
        hwFailedTimes OBJECT-TYPE
            SYNTAX Integer32
            MAX-ACCESS read-only
            STATUS current
            DESCRIPTION
                "
                Times of checking failed
                "
            ::= { hwPingAutoResetEntry 7 }


        -- 1.3.6.1.4.1.2011.6.3.16.1.1.8
        hwAutoResetEnableStatus OBJECT-TYPE
            SYNTAX INTEGER
                {
                enable(1),
                disable(2)
                }
            MAX-ACCESS read-write
            STATUS current
            DESCRIPTION
                "
                Enable status of auto-reset.
                Options:
                1. enable(1)    - enable
                2. disable(2)   - disable
                "
            ::= { hwPingAutoResetEntry 8 }


        -- 1.3.6.1.4.1.2011.6.3.16.1.1.9
        hwAutoResetRowStatus OBJECT-TYPE
            SYNTAX RowStatus
            MAX-ACCESS read-create
            STATUS current
            DESCRIPTION
                "
                RowStatus standard operation
                "
            ::= { hwPingAutoResetEntry 9 }


        -- 1.3.6.1.4.1.2011.6.3.17
        hwSystemResource OBJECT IDENTIFIER ::= { hwDev 17 }


        -- 1.3.6.1.4.1.2011.6.3.17.1
        hwSystemResTable OBJECT-TYPE
            SYNTAX SEQUENCE OF HwSystemResEntry
            MAX-ACCESS not-accessible
            STATUS current
            DESCRIPTION
                "
                The index of this table is hwFrameIndex, hwSlotIndex or hwResType.
                System resource table.
                "
            ::= { hwSystemResource 1 }


        -- 1.3.6.1.4.1.2011.6.3.17.1.1
        hwSystemResEntry OBJECT-TYPE
            SYNTAX HwSystemResEntry
            MAX-ACCESS not-accessible
            STATUS current
            DESCRIPTION
                "
                The index of this entry is hwFrameIndex, hwSlotIndex or hwResType.
                System resource table.
                "
            INDEX { hwFrameIndex, hwSlotIndex, hwResType }
            ::= { hwSystemResTable 1 }


        HwSystemResEntry ::=
            SEQUENCE {
                hwResType
                    INTEGER,
                hwResOverLoad
                    Integer32,
                hwResOccupancy
                    Integer32
             }

        -- 1.3.6.1.4.1.2011.6.3.17.1.1.1
        hwResType OBJECT-TYPE
            SYNTAX INTEGER
                {
                memory(1),
                messageUnits(2),
                cpu(3)
                }
            MAX-ACCESS read-only
            STATUS current
            DESCRIPTION
                "
                System resource type.
                Options:
                1. memory(1)      -indicates the memory resource
                2. messageUnits(2)-indicates the message resource
                3. cpu(3)         -indicates the CPU resource
                "
            ::= { hwSystemResEntry 1 }


        -- 1.3.6.1.4.1.2011.6.3.17.1.1.2
        hwResOverLoad OBJECT-TYPE
            SYNTAX Integer32 (0..100)
            MAX-ACCESS read-write
            STATUS current
            DESCRIPTION
                "
                System resource overload threshold.
                The following two system resources support querying and
                Threshold setting: memory(1), cpu(3).
                Memory(1) and cpu(3) have limited value ranges.
                MessageUnits(2) cannot be set or queried.
                "
            ::= { hwSystemResEntry 2 }


        -- 1.3.6.1.4.1.2011.6.3.17.1.1.3
        hwResOccupancy OBJECT-TYPE
            SYNTAX Integer32 (0..100)
            MAX-ACCESS read-only
            STATUS current
            DESCRIPTION
                "
                System resource occupancy.
                "
            ::= { hwSystemResEntry 3 }
            

        -- 1.3.6.1.4.1.2011.6.3.17.2	
        hwMemOccupancy OBJECT-TYPE
            SYNTAX Integer32 (0..100)
            MAX-ACCESS read-only
            STATUS current
            DESCRIPTION
                "
                System memory occupancy.
                "
            ::= { hwSystemResource 2 }


        -- 1.3.6.1.4.1.2011.6.3.17.3	
        hwCpuOccupancy OBJECT-TYPE
            SYNTAX Integer32 (0..100)
            MAX-ACCESS read-only
            STATUS current
            DESCRIPTION
                "
                System CPU occupancy.
                "
            ::= { hwSystemResource 3 }


        -- 1.3.6.1.4.1.2011.6.3.18
        hwRingAttrTable OBJECT IDENTIFIER ::= { hwDev 18 }


        -- 1.3.6.1.4.1.2011.6.3.18.1
        hwRingFrequency OBJECT-TYPE
            SYNTAX INTEGER
                {
                frequency16HZ(1),
                frequency25HZ(2),
                frequency50HZ(3),
                frequency20HZ(4)
                }
            MAX-ACCESS read-write
            STATUS current
            DESCRIPTION
                "
                Frequency of ring.
                Options:
                1. frequency16HZ(1) --The frequency of ring is 16HZ
                2. frequency25HZ(2) --The frequency of ring is 25HZ
                3. frequency50HZ(3) --The frequency of ring is 50HZ
                4. frequency20HZ(4) --The frequency of ring is 20HZ
                "
            ::= { hwRingAttrTable 1 }


        -- 1.3.6.1.4.1.2011.6.3.18.2
        hwRingacamplitude OBJECT-TYPE
            SYNTAX INTEGER
                {
                acamplitude74Vrms(1),
                acamplitude65Vrms(2),
                acamplitude50Vrms(3),
                acamplitude75Vrms(4),
                acamplitude70Vrms(5)
                }
            MAX-ACCESS read-write
            STATUS current
            DESCRIPTION
                "
                AC amplitude of ring.
                Options:
                1. acamplitude74Vrms(1) --The AC amplitude of ring is 74Vrms
                2. acamplitude65Vrms(2) --The AC amplitude of ring is 65Vrms
                3. acamplitude50Vrms(3) --The AC amplitude of ring is 50Vrms
                4. acamplitude75Vrms(4) --The AC amplitude of ring is 75Vrms
                5. acamplitude70Vrms(5) --The AC amplitude of ring is 70Vrms
                "
            ::= { hwRingAttrTable 2 }


        -- 1.3.6.1.4.1.2011.6.3.18.3
        hwRingdcbias OBJECT-TYPE
            SYNTAX Integer32 (1..2)
            MAX-ACCESS read-write
            STATUS current
            DESCRIPTION
                "
                DC bias of ring.
                Options:
                1 --The DC bias voltage of ring 20V
                2 --The DC bias voltage of ring 30V.
                "
            ::= { hwRingAttrTable 3 }


        -- 1.3.6.1.4.1.2011.6.3.21
        hwIopacketfile OBJECT IDENTIFIER ::= { hwDev 21 }


        -- 1.3.6.1.4.1.2011.6.3.21.1
        hwIopacketfileAdminStatus OBJECT-TYPE
            SYNTAX INTEGER
                {
                deactivepacketfile(0),
                activepacketfile(1)
                }
            MAX-ACCESS read-write
            STATUS current
            DESCRIPTION
                "
                The status of the board software package.
                Options:
                            1. deactivepacketfile(0)-indicates that the status of the board software package is not active.
                2. activepacketfile(1)  -indicates that active the packet file.
                Perform activepacketfile(1), and the system queries all the boards.
                If the software version of a board is inconsistent with the version in the package,
                the software of the board is upgraded to the version in the package.
                Certain boards can be upgraded by a reset operation
                "
            ::= { hwIopacketfile 1 }


        -- 1.3.6.1.4.1.2011.6.3.22
        hwUpgrade OBJECT IDENTIFIER ::= { hwDev 22 }


        -- 1.3.6.1.4.1.2011.6.3.22.1
        hwUpgradeRequestID OBJECT-TYPE
            SYNTAX Integer32
            MAX-ACCESS read-write
            STATUS current
            DESCRIPTION
                "
                The request index for automatic upgrade.
                For automatic upgrade:
                The NMS loads the NE program of the latest version,
                the data or configuration file after upgrade, and the
                package of the board to the active control board of the NE system.
                The NE automatically loads the NE program,
                the data or configuration file after upgrade, and the package,
                    from the active control board to the standby control board in a synchronous manner.
                At this time, the NMS needs to deliver the command of upgrading and resetting
                to the active control board.
                When resetting the control board, you must specify hwUpgradeRequestID,
                hwUpgradeAdmin, hwUpgradeResetInterval.
                The operation is saved as a record entry.
                hwUpgradeRequestID is used to identify this operation. Therefore,
                its value cannot be the same as the operation request ID of another record entry.
                The hwUpgradeRequestID value of -1 indicates there is no upgrade going.
                "
            ::= { hwUpgrade 1 }


        -- 1.3.6.1.4.1.2011.6.3.22.2
        hwUpgradeAdmin OBJECT-TYPE
            SYNTAX INTEGER
                {
                nooperation(-1),
                uninterruptedAutoUpgrade(1),
                upgradeSchedule(2),
                undoUpgradeSchedule(3),
                interruptedAutoUpgrade(4)
                }
            MAX-ACCESS read-write
            STATUS current
            DESCRIPTION
                "
                The command of software active.
                Options:
                1.nooperation(-1)             - default state of the system.
                2.uninterruptedAutoUpgrade(1) - uninterrupted auto upgrade.
                3.upgradeSchedule(2)          - reset system and acitve the software. If you need to active the software
                                                after a certain period,you also need to set hwUpgradeReserveTimeout or
                                                hwUpgradeReserveDateTime.
                4.undoUpgradeSchedule(3)      - negate the operation to active software.
                5.interruptedAutoUpgrade(4)   - interrupted auto upgrade.
                "
            ::= { hwUpgrade 2 }


        -- 1.3.6.1.4.1.2011.6.3.22.3
        hwUpgradeResetInterval OBJECT-TYPE
            SYNTAX Integer32 (-1..1440)
            MAX-ACCESS read-write
            STATUS current
            DESCRIPTION
                "
                The interval to force service boards to reset after the upgrade
                of mainboard has been completed.
                Unit:minute
                "
            ::= { hwUpgrade 3 }


        -- 1.3.6.1.4.1.2011.6.3.22.4
        hwUpgradeTargetVersion OBJECT-TYPE
            SYNTAX OCTET STRING
            MAX-ACCESS read-write
            STATUS current
            DESCRIPTION
                "
                The target version of automatic upgrade.
                For example:  MA5600V800R003C02.
                Allow querying the target version only during automatic upgrade.
                The system configuration management platform is locked during automatic upgrade.
                When you are setting the target version of an object in an upgrade,
                you also need to set hwUpgradeRequestID, hwUpgradeAdmin, and hwUpgradeResetInterval.
                Automatic upgrade requires consistency between the program version
                saved in the standby area of the system and the set target version.
                If the target version is not specified, the system performs automatic
                upgrade according to the version saved in the standby area of the system.
                "
            ::= { hwUpgrade 4 }


        -- 1.3.6.1.4.1.2011.6.3.22.5
        hwUpgradeReserveTimeout OBJECT-TYPE
            SYNTAX Integer32 (-1 | 60..604800)
            MAX-ACCESS read-write
            STATUS current
            DESCRIPTION
                "
                Used to set the delay time of software active, in unit of seconds.
                When you set hwUpgradeReserveTimeout, you also need to set hwUpgradeAdmin to upgradeSchedule(2).
                It is invalid to set both hwUpgradeReserveTimeout and hwUpgradeReserveDateTime.
                The hwUpgradeReserveTimeout value of -1 indicates the delay time of software active is not set.
                "
            ::= { hwUpgrade 5 }


        -- 1.3.6.1.4.1.2011.6.3.22.6
        hwUpgradeReserveDateTime OBJECT-TYPE
            SYNTAX DateAndTime
            MAX-ACCESS read-write
            STATUS current
            DESCRIPTION
                "
                This object is used for setting the date and time of software active.
                When you set hwUpgradeReserveDateTime, you also need to set hwUpgradeAdmin to upgradeSchedule(2).
                It is invalid to set both hwUpgradeReserveDateTime and hwUpgradeReserveTimeout.
                The configured time is the local time, and time zone configuration is not supported.
                "
            ::= { hwUpgrade 6 }


        -- 1.3.6.1.4.1.2011.6.3.22.7
        hwEmergencyCallProtect OBJECT-TYPE
            SYNTAX INTEGER
                {
                disable(1),
                enable(2)
                }
            MAX-ACCESS read-write
            STATUS current
            DESCRIPTION
                "
                This object is used for setting the emergence call protection function.
                If this object is set to enable, the system cannot be reset if the system is processing an emergence call.
                Options:
                1.disable(1)  -  Indicates that the emergence call is disabled.
                2.enable(2)   -  Indicates that the emergence call is enabled.
                "
            ::= { hwUpgrade 7 }


        -- 1.3.6.1.4.1.2011.6.3.22.8
        hwUpgradeCapability OBJECT-TYPE
            SYNTAX BITS
                {
                issu(0),
                ossu(1)
                }
            MAX-ACCESS read-only
            STATUS current
            DESCRIPTION
                "
                The capability of upgrade.
                Options:
                1.issu(0)            - in servers software upgrade.
                2.ossu(1)            - out of servers softer upgrade.
                From left to right, each bit indicates a capability of upgrade.
                If the bit is set to 1, it indicates support the capability.
                If the bit is set to 0, it indicates not support the capability.
                "
            ::= { hwUpgrade 8 }


--  1.3.6.1.4.1.2011.6.3.23
        -- 1.3.6.1.4.1.2011.6.3.23
        hwAgentOntInfoTable OBJECT-TYPE
            SYNTAX SEQUENCE OF HwAgentOntInfoEntry
            MAX-ACCESS not-accessible
            STATUS current
            DESCRIPTION
                "
                The index of this table is hwFrameIndex, hwSlotIndex, hwPortIndex or hwOntIndex.
                OLT agent ONT INFO table.
                For hwFrameIndex, refer to hwFrameTable. For hwSlotIndex, refer to hwSlotTable. For hwPortIndex, refer to hwPortTable.
                "
            ::= { hwDev 23 }


--  1.3.6.1.4.1.2011.6.3.23.1
        -- 1.3.6.1.4.1.2011.6.3.23.1
        hwAgentOntInfoEntry OBJECT-TYPE
            SYNTAX HwAgentOntInfoEntry
            MAX-ACCESS not-accessible
            STATUS current
            DESCRIPTION
                "
                The index of this entry is hwFrameIndex, hwSlotIndex, hwPortIndex or hwOntIndex.
                OLT agent ONT INFO table.
                For hwFrameIndex, refer to hwFrameTable. For hwSlotIndex, refer to hwSlotTable. For hwPortIndex, refer to hwPortTable.
                "
            INDEX { hwFrameIndex, hwSlotIndex, hwPortIndex, hwOntIndex }
            ::= { hwAgentOntInfoTable 1 }


        HwAgentOntInfoEntry ::=
            SEQUENCE {
                hwOntIndex
                    Integer32,
                hwOntState
                    OCTET STRING,
                hwOntType
                    OCTET STRING,
                hwOntVersion
                    OCTET STRING
             }

        -- 1.3.6.1.4.1.2011.6.3.23.1.1
        hwOntIndex OBJECT-TYPE
            SYNTAX Integer32
            MAX-ACCESS not-accessible
            STATUS current
            DESCRIPTION
                "
                ONT ID.
                Parameters hwFrameIndex and hwSlotIndex are obligatory, hwOntIndex and hwPortIndex are optional
                (the setting -1 indicates that the parameter is optional).
                For example, to set the information of all ONTs connected to a specified port returned,
                you can set hwOntIndex to -1; to set the information about the status of all ONTs
                connected to all ports of a specified slot returned, you can set hwPortIndex and hwOntIndex to -1
                "
            ::= { hwAgentOntInfoEntry 1 }


        -- 1.3.6.1.4.1.2011.6.3.23.1.2
        hwOntState OBJECT-TYPE
            SYNTAX OCTET STRING
            MAX-ACCESS read-only
            STATUS current
            DESCRIPTION
                "
                ONT  state.
                data structure:
                --------------------------------------------------------------------------------------------------
                |  m   |  ONT state combination   |  ONT state combination   |        |  ONT state combination   |
                | (2B) |   in Port x              |  in Port y               | .....  |   in Port n              |
                --------------------------------------------------------------------------------------------------
                /                            \
                /                              \
                /                                \
                -----------------------------------
                |  x  | ONT m-1 |       | ONT 0   |
                |(2B) |state(1b)|...... |state(1b)|
                -----------------------------------
                state enum:
                normal(0):     ONT state is normal.
                fault(1):      ONT state is fault.
                "
            ::= { hwAgentOntInfoEntry 2 }


        -- 1.3.6.1.4.1.2011.6.3.23.1.3
        hwOntType OBJECT-TYPE
            SYNTAX OCTET STRING
            MAX-ACCESS read-only
            STATUS current
            DESCRIPTION
                "
                ONT type.
                data structure: ONT IP + ONT type
                -------------------------------------------------------------------
                |  ONT NUM |  ONT IP  | ONT type |          |  ONT IP  | ONT type |
                |   (2B)   |   (4B)   |  (16B)   | ......   |   (4B)   |  (16B)   |
                -------------------------------------------------------------------

                Because of the restrictions on the SNMP packet, the packet of up to 8 KB can be transmitted.
                When the size of the packet to be reported exceeds 8 KB, the packet must be compressed.
                The compress format of the packet is shown in the following figure.
                -----------------------------------------------------------------------
                | DATA-LENGTH | FLAG  |  TLV-NUM  |  TYPE  |  LEN  |  CRC  |          |
                ------------------------------------------------------------          |
                |                                                                     |
                |                                                                     |
                |                                                                     |
                -----------------------------------------------------------------------
                In the compressed packet:
                DATA-LENGTH occupies four bytes to store the whole length of the file, including the header structure.
                FLAG occupies two bytes to store the flag, which indicates the format of the file contents.
                In this compressed packet, the flag indicates that the format of the file contents is compressed.
                0xFEFE indicates compress and 0 indicates non-compress.
                TLV-NUM indicates the number of TLVs that the file carries. In this compressed packet, TLV-NUM is 1,
                indicating the CRC value of the compressed content. The following continuous bytes TYPE, LEN, and CRC
                are data in the TLV format. Each of TYPE, LEN, and CRC occupies two bytes. In this compressed packet,
                TYPE, LEN, and CRC record the CRC value of the compressed content. TYPE indicates the CRC type.
                LEN indicates the number of bytes that the CRC occupies and the actual value is 2.
                CRC stores the CRC value of the compressed content.
                The actual returned content is compressed in the .zip format and stored in the final field of compressed
                content.
                "
            ::= { hwAgentOntInfoEntry 3 }


        -- 1.3.6.1.4.1.2011.6.3.23.1.4
        hwOntVersion OBJECT-TYPE
            SYNTAX OCTET STRING
            MAX-ACCESS read-only
            STATUS current
            DESCRIPTION
                "
                ONT version.
                data structure: ONT IP + ONT version
                ------------------------------------------------------------------------
                |  ONT NUM |  ONT IP  | ONT version |         |  ONT IP  | ONT version |
                |   (2B)   |   (4B)   |  (32B)      | ......  |   (4B)   |  (32B)      |
                ------------------------------------------------------------------------
                "
            ::= { hwAgentOntInfoEntry 4 }


        -- 1.3.6.1.4.1.2011.6.3.24
        hwConfigLock OBJECT IDENTIFIER ::= { hwDev 24 }


        -- 1.3.6.1.4.1.2011.6.3.24.1
        hwConfigLockState OBJECT-TYPE
            SYNTAX INTEGER
                {
                locked(1),
                unlocked(2)
                }
            MAX-ACCESS read-only
            STATUS current
            DESCRIPTION
                "
                Whether the system configuration is locked.
                Options:
                1. locked(1)   -the system configuration is locked
                2. unlocked(2) -the system configuration is not locked
                The user who locks the system configuration can unlock it.
                Super users and the network administrator can forcibly unlock
                the system configuration. Other users cannot unlock it.
                "
            ::= { hwConfigLock 1 }


        -- 1.3.6.1.4.1.2011.6.3.24.2
        hwConfigUnlockInterval OBJECT-TYPE
            SYNTAX Integer32 (1..255)
            MAX-ACCESS read-write
            STATUS current
            DESCRIPTION
                "
                The interval for automatic unlock of the system configuration, in unit of minute.
                The system re-counts the time in these two cases: a user successfully locks the
                system configuration and the user who locks system configuration sets hwConfigUnlockInterval.
                If a user unlocks the system configuration within the automatic unlock interval,
                automatic unlock is not necessary. If the system configuration keeps locked,
                after the interval elapses, the system automatically unlocks it.
                Default: 5
                "
            ::= { hwConfigLock 2 }


        -- 1.3.6.1.4.1.2011.6.3.24.3
        hwConfigLockUserType OBJECT-TYPE
            SYNTAX INTEGER
                {
                nooperation(-1),
                nms(1),
                series(2),
                telnet(3),
                web(4),
                xml(5),
                ssh(6)
                }
            MAX-ACCESS read-only
            STATUS current
            DESCRIPTION
                "
                The type of user who locks system configuration.
                Options:
                1. nooperation(-1) -default type of the system
                2. nms(1)          -the user who access through the NMS
                3. series(2)       -the user who access through the serial interface
                4. telnet(3)       -the user who access through telnet
                5. web(4)          -the user who access through the web user interface
                6. xml(5)          -the user who access through the XML interface
                7. ssh(6)          -the user who access through SSH 
                "
            ::= { hwConfigLock 3 }


        -- 1.3.6.1.4.1.2011.6.3.24.4
        hwConfigLockUserName OBJECT-TYPE
            SYNTAX OCTET STRING
            MAX-ACCESS read-only
            STATUS current
            DESCRIPTION
                "
                The user name of the user who locks the configuration platform.
                "
            ::= { hwConfigLock 4 }


        -- 1.3.6.1.4.1.2011.6.3.24.5
        hwConfigLockUserIPAddr OBJECT-TYPE
            SYNTAX IpAddress
            MAX-ACCESS read-only
            STATUS current
            DESCRIPTION
                "
                The IP address of the user who locks the configuration platform.
                If a user who accesses through the serial port locks the configuration platform,
                the IP address is default value.	
               DEFVAL { 255.255.255.255 }
               "
            ::= { hwConfigLock 5 }


        -- 1.3.6.1.4.1.2011.6.3.24.6
        hwConfigLockOperate OBJECT-TYPE
            SYNTAX INTEGER
                {
                lock(1),
                unlock(2)
                }
            MAX-ACCESS read-write
            STATUS current
            DESCRIPTION
                "
                The operation to lock or unlock config.
                Options:
                1. lock(1)   -before data configuration, use lock(1) to lock the configuration platform,
                              preventing other users from modifying or deleting the configuration data just completed
                2. unlock(2) -when the data configuration is complete, use unlock(2) to unlock the configuration platform.
                              After that, other users can configure the system data
                If a user performs lock(1) and does not perform unlock(2) after data configuration,
                the system automatically unlocks after a certain period.
                For the interval for automatic unlock, refer to hwConfigUnlockInterval.
                "
            ::= { hwConfigLock 6 }


        -- 1.3.6.1.4.1.2011.6.3.25
        hwIntelligentPhoneParaTable OBJECT IDENTIFIER ::= { hwDev 25 }


        -- 1.3.6.1.4.1.2011.6.3.25.1
        hwIntelligentPhoneMode OBJECT-TYPE
            SYNTAX INTEGER
                {
                disable(1),
                enable(2)
                }
            MAX-ACCESS read-write
            STATUS current
            DESCRIPTION
                "
                The switch of Intelligent-phone mode: disable or enable.
                DEFVAL { disable }
                Options:
                1. disable(1) -if it is set to disable(1), the settings of hwAttenuation and hwDetectionThreshold
                               are not applied
                2.enable(2)   -if it is set to enable(2), the settings of hwAttenuation and hwDetectionThreshold
                               take effect in the intelligent pay phone service (IPP)
                "
            ::= { hwIntelligentPhoneParaTable 1 }


        -- 1.3.6.1.4.1.2011.6.3.25.2
        hwAttenuation OBJECT-TYPE
            SYNTAX Integer32 (0..14)
            MAX-ACCESS read-write
            STATUS current
            DESCRIPTION
                "
                The value of Intelligent-signal attenuation:  0 dBm to 14 dBm.
                From 0 to 14 independently indicates form 0 dBm to 14 dBm.
                Default: 5 dBm.
                DEFVAL { 5 }
                "
            ::= { hwIntelligentPhoneParaTable 2 }


        -- 1.3.6.1.4.1.2011.6.3.25.3
        hwDetectionThreshold OBJECT-TYPE
            SYNTAX Integer32 (0..28)
            MAX-ACCESS read-write
            STATUS current
            DESCRIPTION
                "
                The threshold of intelligent-signal detection: 0 dBm to 28 dBm.
                From 0 to 28 independently indicates form 0 dBm to -28 dBm.
                Default: -15 dBm.
                DEFVAL { 15 }
                "
            ::= { hwIntelligentPhoneParaTable 3 }


        -- 1.3.6.1.4.1.2011.6.3.26
        hwPstnBoardCfgTable OBJECT-TYPE
            SYNTAX SEQUENCE OF HwPstnBoardCfgEntry
            MAX-ACCESS not-accessible
            STATUS current
            DESCRIPTION
                "
                The index of this table is hwFrameIndex or hwSlotIndex.
                PstnBoard config table.
                "
            ::= { hwDev 26 }


        -- 1.3.6.1.4.1.2011.6.3.26.1
        hwPstnBoardCfgEntry OBJECT-TYPE
            SYNTAX HwPstnBoardCfgEntry
            MAX-ACCESS not-accessible
            STATUS current
            DESCRIPTION
                "
                The index of this entry is hwFrameIndex or hwSlotIndex.
                PstnBoard config table.
                "
            INDEX { hwFrameIndex, hwSlotIndex }
            ::= { hwPstnBoardCfgTable 1 }


        HwPstnBoardCfgEntry ::=
            SEQUENCE {
                hwPowerMode
                    INTEGER
             }

        -- 1.3.6.1.4.1.2011.6.3.26.1.1
        hwPowerMode OBJECT-TYPE
            SYNTAX INTEGER
                {
                generalMode(0),
                highMode(1)
                }
            MAX-ACCESS read-write
            STATUS current
            DESCRIPTION
                "
                Indicates the power-mode of the board.
                Options:
                1. generalMode(0)  -Indicate that the board uses normal power supply
                2. highMode(1)     -Indicate that the board uses high-voltage power supply
                "
            ::= { hwPstnBoardCfgEntry 1 }

        -- 1.3.6.1.4.1.2011.6.3.27
        hwNatOnuTable OBJECT IDENTIFIER ::= { hwDev 27 }


        -- 1.3.6.1.4.1.2011.6.3.27.1
        hwNatOnuConfigInfoTable OBJECT IDENTIFIER ::= { hwNatOnuTable 1 }


--  1.3.6.1.4.1.2011.6.3.27.1.1
        -- 1.3.6.1.4.1.2011.6.3.27.1.1
        hwNatOnuMgmtSwitch OBJECT-TYPE
            SYNTAX INTEGER
                {
                disable(1),
                enable(2)
                }
            MAX-ACCESS read-only
            STATUS current
            DESCRIPTION
                "
                The status of the function of managing ONU through the NAT
                proxy for OLT: disable or enable.
                Options:
                1.disable(1)    - the state of the function is disabled
                2.enable(2)     - the state of the function is enabled
                "
            ::= { hwNatOnuConfigInfoTable 1 }


--  1.3.6.1.4.1.2011.6.3.27.1.2
        -- 1.3.6.1.4.1.2011.6.3.27.1.2
        hwNatOnuVlanID OBJECT-TYPE
            SYNTAX Integer32 (-1 | 2..4093)
            MAX-ACCESS read-only
            STATUS current
            DESCRIPTION
                "
                The VLANID of the Management Channel which ONU belongs to.
                -1 (default value) indicates this value is not configured.
                "
            ::= { hwNatOnuConfigInfoTable 2 }


        -- 1.3.6.1.4.1.2011.6.3.27.1.3
        hwNatOnuIpAddr OBJECT-TYPE
            SYNTAX IpAddress
            MAX-ACCESS read-only
            STATUS current
            DESCRIPTION
                "
                The public IP Address of ONU under the Agent Management of OLT.
                "
            ::= { hwNatOnuConfigInfoTable 3 }

        -- 1.3.6.1.4.1.2011.6.3.27.1.4
        hwNatOnuPriority OBJECT-TYPE
            SYNTAX Integer32 (0..7)
            MAX-ACCESS read-only
            STATUS current
            DESCRIPTION
                "
                The Priority of the SNMP Message from ONU.
                "
            ::= { hwNatOnuConfigInfoTable 4 }


        -- 1.3.6.1.4.1.2011.6.3.27.1.5
        hwNatOnuStartIp OBJECT-TYPE
            SYNTAX IpAddress
            MAX-ACCESS read-write
            STATUS current
            DESCRIPTION
                "
                The start IP Address of ONU Inner Ip Segment.
                "
            ::= { hwNatOnuConfigInfoTable 5 }

        -- 1.3.6.1.4.1.2011.6.3.27.1.6
        hwNatOnuIpScope OBJECT-TYPE
            SYNTAX Integer32 (1024..5120)
            MAX-ACCESS read-write
            STATUS current
            DESCRIPTION
                "
                The number of ONU Inner Ip.
                "
            ::= { hwNatOnuConfigInfoTable 6 }


        -- 1.3.6.1.4.1.2011.6.3.27.2
        hwNatOnuUDPInfoTable OBJECT-TYPE
            SYNTAX SEQUENCE OF HwNatOnuUDPInfoEntry
            MAX-ACCESS not-accessible
            STATUS current
            DESCRIPTION
                "
                The index of this table is hwFrameIndex, hwSlotIndex, hwPortIndex or hwOntIndex.
                The UDP port distribution table of ONU.
                "
            ::= { hwNatOnuTable 2 }


        -- 1.3.6.1.4.1.2011.6.3.27.2.1
        hwNatOnuUDPInfoEntry OBJECT-TYPE
            SYNTAX HwNatOnuUDPInfoEntry
            MAX-ACCESS not-accessible
            STATUS current
            DESCRIPTION
                "
                The index of this entry is hwFrameIndex, hwSlotIndex, hwPortIndex or hwOntIndex.
                The UDP port distribution table of ONU.
                "
            INDEX { hwFrameIndex, hwSlotIndex, hwPortIndex, hwOntIndex }
            ::= { hwNatOnuUDPInfoTable 1 }


        HwNatOnuUDPInfoEntry ::=
            SEQUENCE {
                hwNatOnuUdpBegin
                    Integer32
             }

        -- 1.3.6.1.4.1.2011.6.3.27.2.1.1
        hwNatOnuUdpBegin OBJECT-TYPE
            SYNTAX Integer32 (0..65528)
            MAX-ACCESS read-only
            STATUS current
            DESCRIPTION
                "
                The start UDP Port Number of ONU which is managed by OLT through NAT.
                "
            ::= { hwNatOnuUDPInfoEntry 1 }


        -- 1.3.6.1.4.1.2011.6.3.28
        hwServiceMigrationTable OBJECT-TYPE
            SYNTAX SEQUENCE OF HwServiceMigrationEntry
            MAX-ACCESS not-accessible
            STATUS current
            DESCRIPTION
                "
                The service migration object table of Port or ONT.
                The objects in hwServiceMigrationTable are used for migrating service operations
                associated with Port or ONT. The operations include adding and deleting a object.
                The indexes of this table are IfIndex, hwServiceMigrationOntId.
                "
            ::= { hwDev 28 }

        -- 1.3.6.1.4.1.2011.6.3.28.1
        hwServiceMigrationEntry OBJECT-TYPE
            SYNTAX HwServiceMigrationEntry
            MAX-ACCESS not-accessible
            STATUS current
            DESCRIPTION
                "
                The service migration object table of Port or ONT.
                The objects in hwServiceMigrationTable are used for migrating service operations
                associated with Port or ONT. The operations include adding and deleting a object.
                The indexes of this entry are IfIndex, hwServiceMigrationOntId.
                "
            INDEX { ifIndex, hwServiceMigrationOntId }
            ::= { hwServiceMigrationTable 1 }


        HwServiceMigrationEntry ::=
            SEQUENCE {
                hwServiceMigrationOntId
                    Integer32,
                hwServiceMigrationRowStatus
                    RowStatus
             }

        -- 1.3.6.1.4.1.2011.6.3.28.1.1
        hwServiceMigrationOntId OBJECT-TYPE
            SYNTAX Integer32
            MAX-ACCESS not-accessible
            STATUS current
            DESCRIPTION
                "
                Ont ID.
                When hwOntId  = 65535, the operating object is Port.
                When hwOntId != 65535, the operating object is ONT.
                "
            ::= { hwServiceMigrationEntry 1 }


        -- 1.3.6.1.4.1.2011.6.3.28.1.2
        hwServiceMigrationRowStatus OBJECT-TYPE
            SYNTAX RowStatus
            MAX-ACCESS read-create
            STATUS current
            DESCRIPTION
                "
                Indicates the row status, used for creating or deleting
                a migration object. createAndGo(4) and destroy(6) are supported.
                During the query operation, active(1) is always returned for this leaf.
                Options:
                1. active(1)      -when this leaf is queried, the value is fixed to active(1).
                2. createAndGo(4) -create a new instance of a conceptual row.
                3. destroy(6)     -delete the instances associated with an existing conceptual row.
                "
            ::= { hwServiceMigrationEntry 2 }


        -- 1.3.6.1.4.1.2011.6.3.29
        hwServiceCfgMngtTable OBJECT-TYPE
            SYNTAX SEQUENCE OF HwServiceCfgMngtEntry
            MAX-ACCESS not-accessible
            STATUS current
            DESCRIPTION
                "
                The service configuration object table of Port or ONT.
                The objects in hwServiceCfgMngtTable are used for configuration operations
                associated with port or ONT. The operations include adding and deleting a object.
                The indexes of this table are IfIndex, hwServiceCfgOntId.
                "
            ::= { hwDev 29 }

        -- 1.3.6.1.4.1.2011.6.3.29.1
        hwServiceCfgMngtEntry OBJECT-TYPE
            SYNTAX HwServiceCfgMngtEntry
            MAX-ACCESS not-accessible
            STATUS current
            DESCRIPTION
                "
                The service configuration object table of Port or ONT.
                The objects in hwServiceCfgMngtTable are used for configuration operations
                associated with port or ONT. The operations include adding and deleting a object.
                The indexes of this entry are IfIndex, hwServiceCfgOntId.
                "
            INDEX { ifIndex, hwServiceCfgOntId }
            ::= { hwServiceCfgMngtTable 1 }


        HwServiceCfgMngtEntry ::=
            SEQUENCE {
                hwServiceCfgOntId
                    Integer32,
                hwServiceCfgOperStatus
                    INTEGER,
                hwServiceCfgRowStatus
                    RowStatus
             }

        -- 1.3.6.1.4.1.2011.6.3.29.1.1
        hwServiceCfgOntId OBJECT-TYPE
            SYNTAX Integer32
            MAX-ACCESS not-accessible
            STATUS current
            DESCRIPTION
                "
                Ont ID.
                When hwOntId  = 65535, the operating object is Port.
                When hwOntId != 65535, the operating object is ONT.
                "
            ::= { hwServiceCfgMngtEntry 1 }

        -- 1.3.6.1.4.1.2011.6.3.29.1.2
        hwServiceCfgOperStatus OBJECT-TYPE
            SYNTAX INTEGER
                {
                srvCfgDeleting(1),
                srvCfgDeletionComplete(2),
                srvCfgDeletionFailed(3)
                }
            MAX-ACCESS read-only
            STATUS current
            DESCRIPTION
                "
                The service configuration object status.
                Options:
                1. srvCfgDeleting(1)           -The operation is in deleting state.
                2. srvCfgDeletionComplete(2)   -The operation success.
                3. srvCfgDeletionFailed(3)     -The operation fail.
                "
            ::= { hwServiceCfgMngtEntry 2 }

        -- 1.3.6.1.4.1.2011.6.3.29.1.3
        hwServiceCfgRowStatus OBJECT-TYPE
            SYNTAX RowStatus
            MAX-ACCESS read-create
            STATUS current
            DESCRIPTION
                "
                Indicates the row status, used for creating or deleting
                a service configuration object. createAndGo(4) and destroy(6)
                are supported. During the query operation, active(1) is
                always returned for this leaf.
                Options:
                1. active(1)      -when this leaf is queried, the value is fixed to active(1).
                2. createAndGo(4) -create a new instance of a conceptual row.
                3. destroy(6)     -delete the instances associated with an existing conceptual row.
                "
            ::= { hwServiceCfgMngtEntry 3 }


        -- 1.3.6.1.4.1.2011.6.3.30
        hwSysCapabilityTable OBJECT-TYPE
            SYNTAX SEQUENCE OF HwSysCapabilityEntry
            MAX-ACCESS not-accessible
            STATUS current
            DESCRIPTION
                "
                Description of the device dynamic capability. The capability value
                is stored in 16 byte(128 bit), each bit denotes one capability,
                1 equals support, 0 equals not.
                The index of this table is hwCapabilityFeatureID.
                "
            ::= { hwDev 30 }


        -- 1.3.6.1.4.1.2011.6.3.30.1
        hwSysCapabilityEntry OBJECT-TYPE
            SYNTAX HwSysCapabilityEntry
            MAX-ACCESS not-accessible
            STATUS current
            DESCRIPTION
                "
                Description of the device dynamic capability. The capability value
                is stored in 16 byte(128 bit), each bit denotes one capability,
                1 equals support, 0 equals not.
                The index of this table is hwCapabilityFeatureID.
                "
            INDEX { hwCapabilityFeatureID }
            ::= { hwSysCapabilityTable 1 }


        HwSysCapabilityEntry ::=
            SEQUENCE {
                hwCapabilityFeatureID
                    INTEGER,
                hwCapabilityFeatureValue
                    OCTET STRING,
                hwCapabilityFeatureMask
                    OCTET STRING
             }

        -- 1.3.6.1.4.1.2011.6.3.30.1.1
        hwCapabilityFeatureID OBJECT-TYPE
            SYNTAX INTEGER { system(1) }
            MAX-ACCESS read-only
            STATUS current
            DESCRIPTION
                "
                The id of device feature.
                Options:
                1.system(1)   - feature of system
                "
            ::= { hwSysCapabilityEntry 1 }


        -- 1.3.6.1.4.1.2011.6.3.30.1.2
        hwCapabilityFeatureValue OBJECT-TYPE
            SYNTAX OCTET STRING (SIZE (16))
            MAX-ACCESS read-only
            STATUS current
            DESCRIPTION
                "
                The vaule of device capability.

                When hwCapabilityFeatureID equals system(1), bit from left to right represents:
                0.AG capability
                1.BFD capability

                The value of the bit is 0 means the capability is not supported.
                The value of the bit is 1 means the capability is supported.
                "
            ::= { hwSysCapabilityEntry 2 }

        -- 1.3.6.1.4.1.2011.6.3.30.1.3
        hwCapabilityFeatureMask OBJECT-TYPE
            SYNTAX OCTET STRING (SIZE (16))
            MAX-ACCESS read-only
            STATUS current
            DESCRIPTION
                "
                The mask of device capability.

                When hwCapabilityFeatureID equals system(1), bit from left to right represents:
                0.AG capability
                1.BFD capability

                The value of the bit is 0 means the 'capability value' is invalid.
                The value of the bit is 1 means the 'capability value' is valid.
                 "
            ::= { hwSysCapabilityEntry 3 }    
          
            
        -- 1.3.6.1.4.1.2011.6.3.31
        hwDevLedLight  OBJECT IDENTIFIER ::= { hwDev 31 }
           
       -- 1.3.6.1.4.1.2011.6.3.31.1
        hwDevLedLightByNms OBJECT-TYPE
            SYNTAX INTEGER
                 {
                 ledOn(1),
                 ledOff(2),
                 null(3)
                 }
            MAX-ACCESS read-write
            STATUS current
            DESCRIPTION
                "
                This node supports the SET operation:
                 If the pre-deployment on the NMS fails, the RUN indicator turns yellow by set ledOn(1). A half
                 an hour later, the yellow indicator automatically turns off.  
                 If the pre-deployment on the NMS is successful, the RUN indicator must be set ledOff(2).
	
                 This node supports the GET operation:
                 The system returns null(3) when the GET operation is performed.
	                
                 1,ledOn(1)		--Network pre-deployment fail.
                 2,ledOff(2)		--Network pre-deployment success.
                 3,null(3)		--The return value of GET operation.
                "
            ::= { hwDevLedLight 1 }


        -- 1.3.6.1.4.1.2011.6.3.32
        hwBandwidth  OBJECT IDENTIFIER ::= { hwDev 32 }

        -- 1.3.6.1.4.1.2011.6.3.32.1
        hwBandwidthMode OBJECT-TYPE
            SYNTAX INTEGER
                 {
                 bandwidth40G(1),
                 bandwidth80G(2),
                 bandwidth160G(3),
                 bandwidth50G(4),
                 bandwidth100G(5),
                 bandwidth200G(6)
                 }
            MAX-ACCESS read-write
            STATUS current
            DESCRIPTION
                "
                Configuring the bandwidth mode of the device.
                Options:
                1.bandwidth40G(1)   - 40G
                2.bandwidth80G(2)   - 80G
                3.bandwidth160G(3)  - 160G
                4.bandwidth50G(4)   - 50G
                5.bandwidth100G(5)  - 100G
                6.bandwidth200G(6)  - 200G
                "
            ::= { hwBandwidth 1 }
            
            
        -- 1.3.6.1.4.1.2011.6.3.103
        hwDevSnmpProbeMonitor  OBJECT IDENTIFIER ::= { hwDev 103 }
 
        -- 1.3.6.1.4.1.2011.6.3.103.1
        hwDevSnmpProbeMonitorPara OBJECT IDENTIFIER ::= { hwDevSnmpProbeMonitor 1 }  
        
        -- 1.3.6.1.4.1.2011.6.3.103.1.1
        hwDevSnmpProbeMonitorSwitch OBJECT-TYPE
            SYNTAX INTEGER
                 {
                 enable(1),
                 disable(2)
                 }                    
            MAX-ACCESS read-write
            STATUS current
            DESCRIPTION
                " 
                The object specifies the switch state of SNMP probe monitor. 
                Options:
                enable(1)  -indicates the SNMP probe monitor switch is on.
                disable(2) -indicates the SNMP probe monitor switch is off.
                Default: enable(1).  
                "
            ::= { hwDevSnmpProbeMonitorPara 1 }  
            
        -- 1.3.6.1.4.1.2011.6.3.103.1.2
        hwDevSnmpProbeMonitorActiveThreshold OBJECT-TYPE
            SYNTAX Integer32 (3..60)
            MAX-ACCESS read-write
            STATUS current
            DESCRIPTION
                "
                The object specifies the active-threshold of SNMP probe monitor.
                From 3 minutes to 60 minutes.
                Default: 15 minutes.
                "
            ::= { hwDevSnmpProbeMonitorPara 2 }
            
       -- 1.3.6.1.4.1.2011.6.3.103.2
        hwDevSnmpProbeHostTable OBJECT-TYPE
            SYNTAX SEQUENCE OF HwDevSnmpProbeHostEntry
            MAX-ACCESS not-accessible 
            STATUS current
         DESCRIPTION
                "
                The SNMP probe monitor table, which supports the functions of querying the information 
                of SNMP probe monitor. The index of this table is hwDevSnmpProbeHostIndex.
                "
            ::= { hwDevSnmpProbeMonitor 2 } 
  
        -- 1.3.6.1.4.1.2011.6.3.103.2.1           
        hwDevSnmpProbeHostEntry OBJECT-TYPE
            SYNTAX HwDevSnmpProbeHostEntry
            MAX-ACCESS not-accessible
            STATUS current
            DESCRIPTION
                "
                The SNMP probe monitor table, which supports the functions of querying the information 
                of SNMP probe monitor. The index of this table is hwDevSnmpProbeHostIndex.
                "
            INDEX { hwDevSnmpProbeHostIndex }
            ::= { hwDevSnmpProbeHostTable 1 } 
            
        HwDevSnmpProbeHostEntry ::=
            SEQUENCE {
                hwDevSnmpProbeHostIndex
                    Integer32,
                hwDevSnmpProbeHostIpAddressType
                    InetAddressType,
                hwDevSnmpProbeHostIpAddress
                    InetAddress,
                hwDevSnmpProbeReceivedCount
                    Integer32,
                hwDevSnmpProbeInitiallyReceivedTime
                    DateAndTime,
                hwDevSnmpProbeRecentlyReceivedTime
                    DateAndTime,
                hwDevSnmpProbeMinimumInterval
                    Integer32,
		        hwDevSnmpProbeMaxmumInterval
                    Integer32,
                hwDevSnmpProbeAverageInterval
                    Integer32
             }
 
        -- 1.3.6.1.4.1.2011.6.3.103.2.1.1              
        hwDevSnmpProbeHostIndex OBJECT-TYPE
            SYNTAX Integer32(0..4)
            MAX-ACCESS read-only
            STATUS current
            DESCRIPTION
                "
                The object specifies the index of SNMP probe monitor.
                "
            ::= { hwDevSnmpProbeHostEntry 1 }

        -- 1.3.6.1.4.1.2011.6.3.103.2.1.2            
        hwDevSnmpProbeHostIpAddressType OBJECT-TYPE
            SYNTAX InetAddressType                   
            MAX-ACCESS read-only
            STATUS current
            DESCRIPTION                
                "
                The object specifies the IP address type of SNMP probe monitor:
                Options:
                ipv4(1)  -indicates an IPv4 address
                ipv6(2)  -indicates an IPv6 address
                "
            ::= { hwDevSnmpProbeHostEntry 2 } 
        
        -- 1.3.6.1.4.1.2011.6.3.103.2.1.3
        hwDevSnmpProbeHostIpAddress OBJECT-TYPE
            SYNTAX InetAddress
            MAX-ACCESS read-only
            STATUS current
            DESCRIPTION
                "
                The object specifies the IP address of SNMP probe monitor.
                "
            ::= { hwDevSnmpProbeHostEntry 3 }

        -- 1.3.6.1.4.1.2011.6.3.103.2.1.4
        hwDevSnmpProbeReceivedCount OBJECT-TYPE
            SYNTAX Integer32
            MAX-ACCESS read-only
            STATUS current
            DESCRIPTION
                "
                The object specifies the total probe count of SNMP probe monitor.
                "
            ::= { hwDevSnmpProbeHostEntry 4 }

        -- 1.3.6.1.4.1.2011.6.3.103.2.1.5
        hwDevSnmpProbeInitiallyReceivedTime OBJECT-TYPE
            SYNTAX DateAndTime
            MAX-ACCESS read-only
            STATUS current
            DESCRIPTION
                "
                The object specifies the initial probe time of SNMP probe monitor.
                "
            ::= { hwDevSnmpProbeHostEntry 5 }              

        -- 1.3.6.1.4.1.2011.6.3.103.2.1.6
        hwDevSnmpProbeRecentlyReceivedTime OBJECT-TYPE
            SYNTAX DateAndTime
            MAX-ACCESS read-only
            STATUS current
            DESCRIPTION
                "
                The object specifies the recent probe time of SNMP probe monitor.
                "
            ::= { hwDevSnmpProbeHostEntry 6 }                       
             
        -- 1.3.6.1.4.1.2011.6.3.103.2.1.7
        hwDevSnmpProbeMinimumInterval OBJECT-TYPE
            SYNTAX Integer32
            MAX-ACCESS read-only
            STATUS current
            DESCRIPTION
                "
                The object specifies the minimum interval of SNMP probe monitor, unit second.
                "
            ::= { hwDevSnmpProbeHostEntry 7 }

        -- 1.3.6.1.4.1.2011.6.3.103.2.1.8
        hwDevSnmpProbeMaxmumInterval OBJECT-TYPE
            SYNTAX Integer32
            MAX-ACCESS read-only
            STATUS current
            DESCRIPTION
                "
                The object specifies the maxmum interval of SNMP probe monitor, unit second.
                "
            ::= { hwDevSnmpProbeHostEntry 8 } 
            
         -- 1.3.6.1.4.1.2011.6.3.103.2.1.9
        hwDevSnmpProbeAverageInterval OBJECT-TYPE
            SYNTAX Integer32
            MAX-ACCESS read-only
            STATUS current
            DESCRIPTION
                "
                The object specifies the average interval of SNMP probe monitor, unit second.
                "
            ::= { hwDevSnmpProbeHostEntry 9 }         

        -- 1.3.6.1.4.1.2011.6.3.103.3
        hwDevSnmpProbeRecordTable OBJECT-TYPE
            SYNTAX SEQUENCE OF HwDevSnmpProbeRecordEntry
            MAX-ACCESS not-accessible
            STATUS current
            DESCRIPTION
                "
                The abnormal record table of SNMP probe monitor, which supports the functions of querying 
                the abnormal record of SNMP probe monitor. The index of this table is hwDevSnmpProbeRecordIndex.
                "
            ::= { hwDevSnmpProbeMonitor 3 }

        -- 1.3.6.1.4.1.2011.6.3.103.3.1           
        hwDevSnmpProbeRecordEntry OBJECT-TYPE
            SYNTAX HwDevSnmpProbeRecordEntry
            MAX-ACCESS not-accessible
            STATUS current
            DESCRIPTION
                "
                The abnormal record table of SNMP probe monitor, which supports the functions of querying 
                the abnormal record of SNMP probe monitor. The index of this table is hwDevSnmpProbeRecordIndex.
                "
            INDEX { hwDevSnmpProbeRecordIndex }
            ::= { hwDevSnmpProbeRecordTable 1 } 
            
        HwDevSnmpProbeRecordEntry ::=
            SEQUENCE {
                hwDevSnmpProbeRecordIndex
                    Integer32,
                hwDevSnmpProbeRecordHostIpAddressType
                    InetAddressType,
                hwDevSnmpProbeRecordHostIpAddress
                    InetAddress,
                hwDevSnmpProbeRecordLastReceivedTime
                    DateAndTime,
                hwDevSnmpProbeRecordReceivedCount
                    Integer32,
		        hwDevSnmpProbeRecordMinimumInterval
                    Integer32,
                hwDevSnmpProbeRecordMaxmumInterval
                    Integer32,
                hwDevSnmpProbeRecordAverageInterval
                    Integer32  
             }
 
        -- 1.3.6.1.4.1.2011.6.3.103.3.1.1              
        hwDevSnmpProbeRecordIndex OBJECT-TYPE
            SYNTAX Integer32(0..49)
            MAX-ACCESS read-only
            STATUS current
            DESCRIPTION
                "
                The object specifies the index of abnormal record.
                "
            ::= { hwDevSnmpProbeRecordEntry 1 }

        -- 1.3.6.1.4.1.2011.6.3.103.3.1.2            
        hwDevSnmpProbeRecordHostIpAddressType OBJECT-TYPE
            SYNTAX InetAddressType                 
            MAX-ACCESS read-only
            STATUS current
            DESCRIPTION                
                "
                The object specifies the IP address type of abnormal record:
                Options:
                ipv4(1)  -indicates an IPv4 address 
                ipv6(2)  -indicates an IPv6 address
                "
            ::= { hwDevSnmpProbeRecordEntry 2 }  
        
        -- 1.3.6.1.4.1.2011.6.3.103.3.1.3
        hwDevSnmpProbeRecordHostIpAddress OBJECT-TYPE
            SYNTAX InetAddress
            MAX-ACCESS read-only
            STATUS current
            DESCRIPTION
                "
                The object specifies the IP address of abnormal record.
                "
            ::= { hwDevSnmpProbeRecordEntry 3 }

        -- 1.3.6.1.4.1.2011.6.3.103.3.1.4
        hwDevSnmpProbeRecordLastReceivedTime OBJECT-TYPE
            SYNTAX DateAndTime
            MAX-ACCESS read-only
            STATUS current
            DESCRIPTION
                "
                The object specifies the last probe time of abnormal record.
                "
            ::= { hwDevSnmpProbeRecordEntry 4 }

        -- 1.3.6.1.4.1.2011.6.3.103.3.1.5
        hwDevSnmpProbeRecordReceivedCount OBJECT-TYPE
            SYNTAX Integer32
            MAX-ACCESS read-only
            STATUS current
            DESCRIPTION
                "
                The object specifies the total probe count of abnormal record.
                "
            ::= { hwDevSnmpProbeRecordEntry 5 }              

        -- 1.3.6.1.4.1.2011.6.3.103.3.1.6
        hwDevSnmpProbeRecordMinimumInterval OBJECT-TYPE
            SYNTAX Integer32
            MAX-ACCESS read-only
            STATUS current
            DESCRIPTION
                "
                The object specifies the minimum interval of abnormal record, unit second.
                "
            ::= { hwDevSnmpProbeRecordEntry 6 }                       
             
        -- 1.3.6.1.4.1.2011.6.3.103.3.1.7
        hwDevSnmpProbeRecordMaxmumInterval OBJECT-TYPE
            SYNTAX Integer32
            MAX-ACCESS read-only
            STATUS current
            DESCRIPTION
                "
                The object specifies the maxmum interval of abnormal record, unit second.
                "
            ::= { hwDevSnmpProbeRecordEntry 7 }

        -- 1.3.6.1.4.1.2011.6.3.103.3.1.8
        hwDevSnmpProbeRecordAverageInterval OBJECT-TYPE
            SYNTAX Integer32
            MAX-ACCESS read-only
            STATUS current
            DESCRIPTION
                "
                The object specifies the average interval of the abnormal record, unit second.
                "
            ::= { hwDevSnmpProbeRecordEntry 8 }


        -- 1.3.6.1.4.1.2011.6.3.34
        hwOntRemoteHttpChnlCfgTable OBJECT-TYPE
            SYNTAX SEQUENCE OF HwOntRemoteHttpChnlCfgEntry
            MAX-ACCESS not-accessible
            STATUS current
            DESCRIPTION
                "
                This table describes parameters that need to be delivered to the OLT and ONT during remote access to the ONT through the web page.
                "
            ::= { hwDev 34 }

        -- 1.3.6.1.4.1.2011.6.3.34.1
        hwOntRemoteHttpChnlCfgEntry OBJECT-TYPE
            SYNTAX HwOntRemoteHttpChnlCfgEntry
            MAX-ACCESS not-accessible
            STATUS current
            DESCRIPTION
                "
                The index of this entry is hwFrameIndex,hwSlotIndex,hwPortIndex,hwOntIndex.
                "
            INDEX { hwFrameIndex, hwSlotIndex, hwPortIndex, hwOntIndex }
            ::= { hwOntRemoteHttpChnlCfgTable 1 }

            HwOntRemoteHttpChnlCfgEntry ::=
            SEQUENCE {
                hwOntRemoteHttpChnlVlan
                    Integer32,
                hwOntRemoteHttpChnlIpAddress
                    IpAddress,
                hwOntRemoteHttpChnlHttpPort
                    Integer32,
                hwOntRemoteHttpChnlProtocol
                    INTEGER,
                hwOntRemoteHttpChnlUserName
                    OCTET STRING,
                hwOntRemoteHttpChnlPassword
                    OCTET STRING,
                hwOntRemoteHttpChnlDuration
                    Integer32,
                hwOntRemoteHttpProxyPort
                    Integer32,
                hwOntRemoteHttpProxyStatus
                    INTEGER,
                hwOntRemoteHttpChnlRowStatus
                    RowStatus
             }

        -- 1.3.6.1.4.1.2011.6.3.34.1.1
        hwOntRemoteHttpChnlVlan OBJECT-TYPE
            SYNTAX Integer32 (1..4096)
            MAX-ACCESS read-create
            STATUS current
            DESCRIPTION
                "
                Indicates the VLAN ID of the ONT. If this parameter is not specified, 
                the system automatically obtains an unoccupied VLAN ID and uses it as the default VLAN ID.
                "
            ::= { hwOntRemoteHttpChnlCfgEntry 1 }

        -- 1.3.6.1.4.1.2011.6.3.34.1.2
        hwOntRemoteHttpChnlIpAddress OBJECT-TYPE
            SYNTAX IpAddress
            MAX-ACCESS read-create
            STATUS current
            DESCRIPTION
                "
                Indicates the IP address of the ONT. 
                If this parameter is not specified, the system selects an unoccupied IP address and uses it as the default IP address.
                "
            ::= { hwOntRemoteHttpChnlCfgEntry 2 }

        -- 1.3.6.1.4.1.2011.6.3.34.1.3
        hwOntRemoteHttpChnlHttpPort OBJECT-TYPE
            SYNTAX Integer32 (0..65528)
            MAX-ACCESS read-create
            STATUS current
            DESCRIPTION
                "
                 Indicates the web server port of the ONT. If this parameter is not specified, port 80 is used by default.
                "
            ::= { hwOntRemoteHttpChnlCfgEntry 3 }

        -- 1.3.6.1.4.1.2011.6.3.34.1.4
        hwOntRemoteHttpChnlProtocol OBJECT-TYPE
            SYNTAX INTEGER
                 {
                   http(1),
                   https(2)
                 }
            MAX-ACCESS read-create
            STATUS current
            DESCRIPTION
                "
                Indicates the protocol type of the web server of the ONT. If this parameter is not specified, HTTPS protocol is used by default.
                "
            ::= { hwOntRemoteHttpChnlCfgEntry 4 }

        -- 1.3.6.1.4.1.2011.6.3.34.1.5
        hwOntRemoteHttpChnlUserName OBJECT-TYPE
            SYNTAX OCTET STRING  (SIZE (0..32))
            MAX-ACCESS read-create
            STATUS current
            DESCRIPTION
                "
                 Indicates the user name used for a temporary user to log in to the web server of the ONT. 
                 If this parameter is not specified, the existing user name and password are used for login.
                "
            ::= { hwOntRemoteHttpChnlCfgEntry 5 }

        -- 1.3.6.1.4.1.2011.6.3.34.1.6
        hwOntRemoteHttpChnlPassword OBJECT-TYPE
            SYNTAX OCTET STRING  (SIZE (0..32))
            MAX-ACCESS read-create
            STATUS current
            DESCRIPTION
                "
                 Indicates the password used for a temporary user to log in to the web server of the ONT, 
                 which can consist of numbers, uppercase letters, lowercase letters, and special characters.
                 And use at least 6 characters.
                "
            ::= { hwOntRemoteHttpChnlCfgEntry 6 } 

        -- 1.3.6.1.4.1.2011.6.3.34.1.7
        hwOntRemoteHttpProxyPort OBJECT-TYPE
            SYNTAX Integer32 (0..65528)
            MAX-ACCESS read-only
            STATUS current
            DESCRIPTION
                "
                 Indicates the port ID of the TCP proxy during remote access to the ONT from the OLT through the web page, which is port 8024 fixedly.
                "
            ::= { hwOntRemoteHttpChnlCfgEntry 7 }

        -- 1.3.6.1.4.1.2011.6.3.34.1.8
        hwOntRemoteHttpChnlDuration OBJECT-TYPE
            SYNTAX Integer32 (0..120)
            MAX-ACCESS read-create
            STATUS current
            DESCRIPTION
                "
                 Indicates the ONT login duration of a temporary user (unit: minute). 
                 If this parameter is not specified, the login duration is 30 minutes by default. 
                "
            ::= { hwOntRemoteHttpChnlCfgEntry 8 }

        -- 1.3.6.1.4.1.2011.6.3.34.1.9
        hwOntRemoteHttpProxyStatus OBJECT-TYPE
            SYNTAX INTEGER 
                 {
                   enable(1),
                   disable(2)
                 }
            MAX-ACCESS read-only
            STATUS current
            DESCRIPTION
                "
                 Indicates the enabling status of the TCP proxy. The initial state is disable.
                "
            ::= { hwOntRemoteHttpChnlCfgEntry 9 } 

        -- 1.3.6.1.4.1.2011.6.3.34.1.10
        hwOntRemoteHttpChnlRowStatus OBJECT-TYPE
            SYNTAX RowStatus
            MAX-ACCESS read-create
            STATUS current
            DESCRIPTION
                "
                Indicates the row status, used for creating or deleting
                a service configuration object. createAndGo(4) and destroy(6)
                are supported. During the query operation, active(1) is
                always returned for this leaf.
                Options:
                2. createAndGo(4) -create a new instance of a conceptual row.
                3. destroy(6)     -delete the instances associated with an existing conceptual row.
                "
            ::= { hwOntRemoteHttpChnlCfgEntry 10 }

    END
